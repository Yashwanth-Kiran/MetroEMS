-- =============================================================================
-- 
-- Proxim Corporation - Access Point Development Division
-- NAC Campus, Hi-Tex Road,
-- Kondapur, Hyderabad  500 034
-- Ph: +91 40 2311 7400, Fax: +91 40 2311 5491,
-- www.proxim.com
-- 
-- =============================================================================
-- 
-- PROXIM Management Information Base (MIB)
-- 
-- =============================================================================
-- 
-- FILENAME:    PXM-SNMP.mib
-- 
-- DESIGNER:    Pavan Sudheer Rampalli (PSR)
-- 
-- TITLE:       PROXIM Management Information Base
-- 
-- USED IN:     PROXIM Next Generation Product Line for SNMP Management. This
--              MIB is intended for the following products:
--                  Access Point Products
--                  Broadband Gateway Products
--                  Tsunami Multi-point Products
-- 
-- =============================================================================
-- 
-- Document History Information
-- 
-- =============================================================================
-- 
-- Version  Date            Authors                        Decription
-- 
-- =============================================================================
-- v0.0.1   August 11       Proxim                   Created the MIB
--          2008
-- v0.1.0   January 12      Proxim                   Added the WORP module
--          2009                                     objects
-- v0.2.0   May 12          Proxim                   Added the support 
--          2009                                     to Monaco MP11 products
-- v0.2.1   July 11         Proxim                   Added the support
--          2009                                     to Monaco QB11 products
-- v2.0.0   Feb 19          Proxim                   Added the support for
--          2010                                     DFS,DDRS,TBC,IGMP snooping
--                                                   and Storm threshold filters
-- v2.2.0   Sep 28          Proxim                   Added the support for
--          2010                                     DDRS min SNR table.
--                                                   Deprecated mib wirelessInActivityTimer
-- v2.3.5   May 17          Proxim                   Added the support for
--          2011                                     Wireless SNR info table,few WORP station and
--                                                   site survey statistics
-- v2.4.0   Oct 24          Proxim                   Added the support for PPPoE,IP Tunneling,
--          2011                                     MCB,Frequency filters,ATPC features and some
--                                                   modifications in TPC feature.
--                                                   Deprecated mibs are wirelessIfTPC,wirelessIfCellSize,
--                                                   wirelessIfActiveTPC,dhcpMaxLeaseTime,
--                                                   dhcpServerDefaultLeaseTime and sysMonitorCPUUsage
-- v2.5.0   April 25        Proxim                   Added the support for 
--          2012                                     Spectrum Analyzer,Roaming,
--                                                   Traps,DNS Proxy,Max Tx Power,
--                                                   Country Legacy 5GHz,Vlan enhancements, 
--                                                   and WORP Thresholds for generating Traps.
--                                                   Deprecated mib wirelessIfDDRSIncrAvgSNRThrld
-- v2.5.1   June 26         Proxim                   Added the support for 
--          2012                                     Country Japan 5.6GHz and US 5.8GHz
-- v2.6.0   Dec 17          Proxim                   Added the support for WORP Link Profile,
--          2012                                     Profile Peer Table, IPv6, Configuration Profiles,
--                                                   BSU Redundancy, DCS, EU SKU and JP SKU, Roaming
--                                                   and PPPoE Enhancements. Few mibs are deprecated.
-- =============================================================================
-- =============================================================================
-- =============================================================================
-- COMPILERS:   NuDesign, iReasoning MIB Compilers
-- 
-- =============================================================================
-- =============================================================================
--             Copyright (C) 2008 Proxim Corporation
--               Proxim Corporation - PROPRIETARY
--  Disclosure to third parties or reproduction in any from
--  whatsoever, without prior written consent, is strictly forbiden.
-- =============================================================================
-- =============================================================================
-- PROXIM MIB Begin
-- =============================================================================

PROXIMTMP-MIB DEFINITIONS ::= BEGIN

IMPORTS
	NOTIFICATION-TYPE, OBJECT-TYPE, MODULE-IDENTITY, 
	enterprises, Counter64, Counter32, TimeTicks, IpAddress, Integer32, Unsigned32
		FROM SNMPv2-SMI
	TEXTUAL-CONVENTION, PhysAddress, RowStatus, 
	MacAddress, DisplayString
		FROM SNMPv2-TC
	InetAddress
		FROM INET-ADDRESS-MIB;

-- =============================================================================
-- PROXIM MIB Imports
-- =============================================================================
--   ifIndex
-- FROM RFC1213-MIB;
-- =============================================================================
-- PROXIM MIB Module Identity: proxim
-- =============================================================================

proxim MODULE-IDENTITY
	LAST-UPDATED "200808110000Z"
	ORGANIZATION 
		"Proxim Corporation"
	CONTACT-INFO 
		"Pavan Sudheer Rampalli
		 Proxim Corporation
		 Access Point Development Division
		 NAC Campus, Hi-Tex Road,
		 Kondapur, Hyderabad  500 034
		 INDIA
		 Tel:   +91.40.2311.7400
		 Fax:   +91.40.2311.5491
		 Email: pavan@proxim.com"
	DESCRIPTION 
		"MIB Definition used in the Proxim Wireless Product Line:
		         iso(1).org(3).dod(6).internet(1).private(4).enterprises(1).
		         proxim(841)"

	REVISION "200808110000Z"
	DESCRIPTION 
		"The latest version of this MIB module"
::= { enterprises 841 }


DisplayString20 ::= TEXTUAL-CONVENTION
	STATUS     current
	DESCRIPTION 
		"The DisplayString20 textual convention is used to define a
		        string that can consist of 0 - 20 alphanumeric characters."
	SYNTAX  OCTET STRING (SIZE(0..20))


DisplayString32 ::= TEXTUAL-CONVENTION
	STATUS     current
	DESCRIPTION 
		"The DisplayString32 textual convention is used to define a
		        string that can consist of 0 - 32 alphanumeric characters."
	SYNTAX  OCTET STRING (SIZE(0..32))


DisplayString55 ::= TEXTUAL-CONVENTION
	STATUS     current
	DESCRIPTION 
		"The DisplayString32 textual convention is used to define a
		        string that can consist of 0 - 55 alphanumeric characters this textual
		        convention is used for Temperature log messages."
	SYNTAX  OCTET STRING (SIZE(0..55))


DisplayString80 ::= TEXTUAL-CONVENTION
	STATUS     current
	DESCRIPTION 
		"The DisplayString80 textual convention is used to define a
		        string that can consist of 0 - 80 alphanumeric characters."
	SYNTAX  OCTET STRING (SIZE(0..80))


InterfaceBitmask ::= TEXTUAL-CONVENTION
	STATUS     current
	DESCRIPTION 
		"An Interface Bitmask used to enable or disable access or
		        functionality of an interface in the system.  Each bit in this
		        object represents a network interface in the system consistent
		        with the ifIndex object in MIB-II.  The value for this object is
		        interpreted as a bitfield, where the value of 1 means enabled.
		        Examples of Usage:
		        1. For a system with the following interfaces :
		         - Ethernet If = 1
		         - Loopback If = 2
		         - Wireless If 0 VAP 0 = 3
		         - Wireless If 0 VAP 1 = 4
		         - Wireless If 0 VAP 2 = 5
		         - Wireless If 0 VAP 3 = 6
		         - Wireless If 1 VAP 0 = 7
		         - Wireless If 1 VAP 1 = 8
		         - Wireless If 1 VAP 2 = 9
		         - Wireless If 1 VAP 3 = 10
		        Interface Bitmask usage:
		         - 00000000 (0x00): All Interfaces disabled
		         - 00000001 (0x01): Ethernet If enabled
		         - 00000010 (0x02): Wireless If 0 VAP 0 enabled
		         - 00000100 (0x03): Wireless If 0 VAP 1 enabled
		         - 00001000 (0x04): Wireless If 0 VAP 2 enabled
		         - 00010000 (0x06): Wireless If 0 VAP 3 enabled
		         TBD: This has to be re-considered
		        Note: The software loopback interface bit is ignored in the
		        usage of the interface bitmask object."
	SYNTAX  Unsigned32 (0..255)


ObjStatus ::= TEXTUAL-CONVENTION
	STATUS     current
	DESCRIPTION 
		"The status textual convention is used to enable or disable
		        functionality or a feature."
	SYNTAX  INTEGER {
		notSupported (0),
		enable (1),
		disable (2)
	}


ObjStatusActive ::= TEXTUAL-CONVENTION
	STATUS     current
	DESCRIPTION 
		"The status textual convention is used to activate, deactivate, and
		        delete a table row."
	SYNTAX  INTEGER {
		active (1),
		inactive (2),
		deleted (3)
	}


Password ::= TEXTUAL-CONVENTION
	STATUS     current
	DESCRIPTION 
		"This represents a textual convention for password feilds."
	SYNTAX  OCTET STRING (SIZE(6..32))


V3Password ::= TEXTUAL-CONVENTION
	STATUS     current
	DESCRIPTION 
		"This represents a textual convention for password feilds."
	SYNTAX  OCTET STRING (SIZE(8..32))


-- =============================================================================
-- Definition of Textual Conventions
-- =============================================================================

VlanId ::= TEXTUAL-CONVENTION
	STATUS     current
	DESCRIPTION 
		"A 12-bit VLAN ID used in the VLAN Tag header."
	SYNTAX  Integer32 (-1..4094)


WEPKeyType ::= TEXTUAL-CONVENTION
	STATUS     current
	DESCRIPTION 
		"The WEPKeyType textual convention is used to define the object
		        type used to configured WEP Keys."
	SYNTAX  OCTET STRING (SIZE(0..32))


-- =============================================================================
-- Definition of the proxim MIB Objects: proxim
-- =============================================================================

wireless             OBJECT IDENTIFIER ::= { proxim 1 }

-- =============================================================================
-- Definition of the wireless MIB Objects: wireless
-- =============================================================================

objects              OBJECT IDENTIFIER ::= { wireless 1 }

-- =============================================================================
-- Definition of the Management MIB Object Main Groups 
-- =============================================================================
-- Device Configuration Group

deviceConfig         OBJECT IDENTIFIER ::= { objects 1 }

-- =============================================================================
-- Definition of the Device Configuration MIB Object Groups
-- =============================================================================
-- Interface Group

interface            OBJECT IDENTIFIER ::= { deviceConfig 1 }

-- =============================================================================
-- Definition of the Interface MIB Object Subgroups
-- =============================================================================
-- Wireless Interface Subgroup

wirelessIf           OBJECT IDENTIFIER ::= { interface 1 }

-- Wireless Interface Roaming Subgroup

wirelessIfRoamingTable  OBJECT IDENTIFIER ::= { wirelessIf 8 }

-- Wireless Interface Scan Across BandWidth Subgroup

wirelessIfScanAcrossBandWidthTable  OBJECT IDENTIFIER ::= { wirelessIf 11 }

-- Wireless Interface Scan Across Offset Subgroup

wirelessIfScanAcrossOffsetTable  OBJECT IDENTIFIER ::= { wirelessIf 12 }

-- Ethernet Interface Subgroup

ethernetIf           OBJECT IDENTIFIER ::= { interface 2 }

-- Security Group

apSecurity           OBJECT IDENTIFIER ::= { deviceConfig 2 }

-- =============================================================================
-- Definition of the Security Subgroups
-- =============================================================================
-- Wireless Security Subgroup

wirelessSecurity     OBJECT IDENTIFIER ::= { apSecurity 1 }

-- Radius Security Subgroup

radius               OBJECT IDENTIFIER ::= { apSecurity 2 }

-- MAC ACL Security Subgroup

macacl               OBJECT IDENTIFIER ::= { apSecurity 3 }

-- QoS Group

qos                  OBJECT IDENTIFIER ::= { deviceConfig 3 }

-- =============================================================================
-- Definition of the QoS Subgroups
-- =============================================================================
-- Wireless QoS Subgroup

wirelessQoS          OBJECT IDENTIFIER ::= { qos 3 }

-- L2 QoS Subgroup

l2l3QoS              OBJECT IDENTIFIER ::= { qos 4 }

-- WORP QoS Sugroup

worpQoS              OBJECT IDENTIFIER ::= { qos 5 }

-- Network Group

network              OBJECT IDENTIFIER ::= { deviceConfig 4 }

-- =============================================================================
-- Definition of the Network Subgroups
-- =============================================================================
-- Network IP address Subgroup

netIp                OBJECT IDENTIFIER ::= { network 1 }

-- Network Configuration Subgroup

netCfg               OBJECT IDENTIFIER ::= { network 2 }

-- Network Address Translation Subgroup

nat                  OBJECT IDENTIFIER ::= { network 3 }

-- Routing Information Protocol (RIP) Subgroup

rip                  OBJECT IDENTIFIER ::= { network 4 }

-- Tunneling Configuration Subgroup

tunneling            OBJECT IDENTIFIER ::= { network 5 }

-- PPPOE (Point-to-point over ethernet protocol) Subgroup

pppoe                OBJECT IDENTIFIER ::= { network 6 }

-- VLAN Group

vlan                 OBJECT IDENTIFIER ::= { deviceConfig 5 }

-- Filtering Group

filtering            OBJECT IDENTIFIER ::= { deviceConfig 6 }

-- =============================================================================
-- Definition of the Filtering Subgroups
-- =============================================================================
-- Protocol Filter Subgroup

protocolFilter       OBJECT IDENTIFIER ::= { filtering 3 }

-- Static Mac Address Filter Subgroup

staticMACAddrFilter  OBJECT IDENTIFIER ::= { filtering 4 }

-- Advanced Filtering Subgroup

advancedFiltering    OBJECT IDENTIFIER ::= { filtering 5 }

-- Port Filter Subgroup

tcpudpPortFilter     OBJECT IDENTIFIER ::= { filtering 6 }

-- Intracell Blocking Subgroup

worpIntraCellBlocking  OBJECT IDENTIFIER ::= { filtering 7 }

-- Security Gateway Subgroup

securityGateway      OBJECT IDENTIFIER ::= { filtering 8 }

-- Storm Threshold Subgroup

stormThreshold       OBJECT IDENTIFIER ::= { filtering 10 }

-- DHCP Group

dhcp                 OBJECT IDENTIFIER ::= { deviceConfig 7 }

-- =============================================================================
-- Definition of the DHCP Subgroups
-- =============================================================================
-- DHCP Server Subgroup

dhcpServer           OBJECT IDENTIFIER ::= { dhcp 1 }

-- DHCP Relay Subgroup

dhcpRelay            OBJECT IDENTIFIER ::= { dhcp 2 }

-- System Coniguration Group

sysConf              OBJECT IDENTIFIER ::= { deviceConfig 8 }

-- LED Stack Group

sysLEDStack          OBJECT IDENTIFIER ::= { sysConf 7 }

-- IGMP Configuration Group

igmp                 OBJECT IDENTIFIER ::= { deviceConfig 10 }

-- Device Management Group

deviceMgmt           OBJECT IDENTIFIER ::= { objects 2 }

-- =============================================================================
-- Definition of the Device Management MIB Object Groups
-- =============================================================================
-- System Group

sys                  OBJECT IDENTIFIER ::= { deviceMgmt 1 }

-- =============================================================================
-- Definition of the System Subgroups
-- =============================================================================
-- System Inventory Management Subgroup

sysInvMgmt           OBJECT IDENTIFIER ::= { sys 2 }

-- System Feature Subgroup

sysFeature           OBJECT IDENTIFIER ::= { sys 3 }

-- System Management Subgroup

sysMgmt              OBJECT IDENTIFIER ::= { sys 4 }

-- System Information

sysInfo              OBJECT IDENTIFIER ::= { sys 5 }

-- SNMP Group

mgmtSnmp             OBJECT IDENTIFIER ::= { deviceMgmt 2 }

-- HTTP Group

http                 OBJECT IDENTIFIER ::= { deviceMgmt 3 }

-- Telnet Group

telnet               OBJECT IDENTIFIER ::= { deviceMgmt 4 }

-- TFTP Group

tftp                 OBJECT IDENTIFIER ::= { deviceMgmt 5 }

-- Trap Control Group 

trapControl          OBJECT IDENTIFIER ::= { deviceMgmt 6 }

-- Management Access Control Group

mgmtAccessControl    OBJECT IDENTIFIER ::= { deviceMgmt 7 }

-- SSH Group

ssh                  OBJECT IDENTIFIER ::= { deviceMgmt 8 }

-- Auto Config Recovery Group

autoConfigRecovery   OBJECT IDENTIFIER ::= { deviceMgmt 9 }

-- HTTPS Group

https                OBJECT IDENTIFIER ::= { deviceMgmt 10 }

-- Bluetooth parameters

ble                  OBJECT IDENTIFIER ::= { deviceMgmt 11 }

-- Monitoring Group

deviceMon            OBJECT IDENTIFIER ::= { objects 3 }

-- =============================================================================
-- Definition of the Device Monitoring MIB Object Groups
-- =============================================================================
-- Syslog Group

syslog               OBJECT IDENTIFIER ::= { deviceMon 1 }

-- Event Log Group

eventlog             OBJECT IDENTIFIER ::= { deviceMon 2 }

-- SNTP Group

sntp                 OBJECT IDENTIFIER ::= { deviceMon 3 }

-- Wireless Interface Monitoring Group

wirelessIfMon        OBJECT IDENTIFIER ::= { deviceMon 4 }

-- =============================================================================
-- Definition of the Wireless Interface Station Statistics Subgroups
-- =============================================================================

wirelessIfStaStats   OBJECT IDENTIFIER ::= { wirelessIfMon 1 }

-- =============================================================================
-- Definition of the Wireless Interface Station Statistics Subgroups
-- =============================================================================

wirelessIfWORPStats  OBJECT IDENTIFIER ::= { wirelessIfMon 2 }

-- =============================================================================
-- Definition of the Wireless Interface Blacklisted information Subgroups
-- =============================================================================

wirelessIfBlacklistInfo  OBJECT IDENTIFIER ::= { wirelessIfMon 3 }

-- =============================================================================
-- Definition of the Wireless Interface (WORP) Link Test Subgroups
-- =============================================================================

wirelessIfWORPLinkTest  OBJECT IDENTIFIER ::= { wirelessIfMon 4 }

-- =============================================================================
-- Definition of the Wireless Interface Statistics Subgroups
-- =============================================================================

wirelessIfStats      OBJECT IDENTIFIER ::= { wirelessIfMon 5 }

-- =============================================================================
-- Definition of the Wireless Interface Statistics Subgroups
-- =============================================================================

wirelessIfSnrInfo    OBJECT IDENTIFIER ::= { wirelessIfMon 6 }

-- =============================================================================
-- Definition of the Wireless Interface Statistics Subgroups
-- =============================================================================

wirelessIfDFSInfo    OBJECT IDENTIFIER ::= { wirelessIfMon 7 }

-- Radius Server Client Stats Group

radiusMon            OBJECT IDENTIFIER ::= { deviceMon 5 }

-- =============================================================================
-- Definition of the Radius Monitoring Statistics Subgroups
-- =============================================================================

radiusClientStats    OBJECT IDENTIFIER ::= { radiusMon 1 }

-- Traps Group

traps                OBJECT IDENTIFIER ::= { deviceMon 6 }

-- =============================================================================
-- Definition of the Traps MIB Object Subgroups 
-- =============================================================================
-- Interface Traps Group

interfaceTraps       OBJECT IDENTIFIER ::= { traps 1 }

-- Security Traps Group

securityTraps        OBJECT IDENTIFIER ::= { traps 2 }

-- Operational Traps Group

operationalTraps     OBJECT IDENTIFIER ::= { traps 3 }

-- System Traps Group

systemTraps          OBJECT IDENTIFIER ::= { traps 4 }

-- SNTP Traps Group

sntpTraps            OBJECT IDENTIFIER ::= { traps 5 }

-- Image Traps Group

imageTraps           OBJECT IDENTIFIER ::= { traps 6 }

-- Network Traps Group

networkTraps         OBJECT IDENTIFIER ::= { traps 7 }

-- Tftp Traps Group

tftpTraps            OBJECT IDENTIFIER ::= { traps 8 }

-- WORP Traps Group

worpTraps            OBJECT IDENTIFIER ::= { traps 9 }

-- Spectrum Analyzer Traps Group

spectrumAnalyzerTraps  OBJECT IDENTIFIER ::= { traps 10 }

-- Site Survey Group

siteSurvey           OBJECT IDENTIFIER ::= { deviceMon 7 }

-- =============================================================================
-- Definition of the Site Survey MIB Object Subgroups 
-- =============================================================================
-- WORP Site Survery Group

worpSiteSurvey       OBJECT IDENTIFIER ::= { siteSurvey 1 }

-- Temperature Log Group

temperature          OBJECT IDENTIFIER ::= { deviceMon 8 }

-- System Monitoring Group

sysMonitor           OBJECT IDENTIFIER ::= { deviceMon 9 }

-- LED Stack

sysMonLEDStack       OBJECT IDENTIFIER ::= { sysMonitor 3 }

-- IGMP Stats

igmpStats            OBJECT IDENTIFIER ::= { deviceMon 10 }

-- =============================================================================
-- Definition of the IGMP Stats MIB Object Subgroups 
-- =============================================================================
-- IGMP Snooping Stats for ethernet interface

igmpEthernetSnoopingStats  OBJECT IDENTIFIER ::= { igmpStats 1 }

-- IGMP Snooping Stats for wireless interface

igmpWirelessSnoopingStats  OBJECT IDENTIFIER ::= { igmpStats 2 }

-- Debug log

debugLog             OBJECT IDENTIFIER ::= { deviceMon 11 }

-- Scan Devices

scanDevices          OBJECT IDENTIFIER ::= { deviceMon 12 }

-- Active Vlan

activeVLAN           OBJECT IDENTIFIER ::= { deviceMon 15 }

-- Spectrum Analyzer

spectrumAnalyzer     OBJECT IDENTIFIER ::= { deviceMon 16 }

-- RLT

rlt                  OBJECT IDENTIFIER ::= { deviceMon 17 }

-- Products

products             OBJECT IDENTIFIER ::= { proxim 2 }

-- =============================================================================
-- Definition of the products MIB Objects: products
-- =============================================================================

ap-800               OBJECT IDENTIFIER ::= { products 1 }
ap-8000              OBJECT IDENTIFIER ::= { products 2 }
ap-8100              OBJECT IDENTIFIER ::= { products 3 }
qb-8100              OBJECT IDENTIFIER ::= { products 11 }
qb-125               OBJECT IDENTIFIER ::= { products 16 }
mp-8100              OBJECT IDENTIFIER ::= { products 21 }
mp-8100-cpe          OBJECT IDENTIFIER ::= { products 22 }
mesh-max             OBJECT IDENTIFIER ::= { products 31 }
mp-825               OBJECT IDENTIFIER ::= { products 41 }
mp-125               OBJECT IDENTIFIER ::= { products 51 }

-- =============================================================================
-- Interface Group Objects
-- =============================================================================
-- =============================================================================
-- The Wireless Interface Subgroup: wirelessIf
-- =============================================================================
-- Wireless Interface properties Table

wirelessIfPropertiesTable  OBJECT-TYPE
	SYNTAX SEQUENCE OF WirelessIfPropertiesTableEntry
	MAX-ACCESS not-accessible
	STATUS     current
	DESCRIPTION 
		"This table contains information on the properties and  
		         capabilities of the wireless interface(s) present in the device."
	::= { wirelessIf 1 }

wirelessIfPropertiesTableEntry  OBJECT-TYPE
	SYNTAX 	WirelessIfPropertiesTableEntry
	MAX-ACCESS not-accessible
	STATUS     current
	DESCRIPTION 
		"This parameter represents the entry in the wireless interface  
		         properties table."
	INDEX { wirelessIfPropertiesTableIndex }
	::= { wirelessIfPropertiesTable 1 }

WirelessIfPropertiesTableEntry ::= SEQUENCE {
	wirelessIfPropertiesTableIndex
		Unsigned32,
	wirelessIfPropertiesRadioStatus
		INTEGER,
	wirelessIfOperationalMode
		DisplayString,
	wirelessIfSupportedOperationalMode
		DisplayString,
	wirelessIfCurrentChannelBandwidth
		Unsigned32,
	wirelessIfSupportedChannelBandwidth
		DisplayString,
	wirelessIfAutoChannelSelection
		INTEGER,
	wirelessIfCurrentOperatingChannel
		Unsigned32,
	wirelessIfSupportedChannels
		OCTET STRING,
	wirelessIfAutoRateSelection
		INTEGER,
	wirelessIfTransmittedRate
		Unsigned32,
	wirelessIfSupportedRate
		DisplayString,
	wirelessIfVAPRTSThreshold
		Unsigned32,
	wirelessIfVAPBeaconInterval
		Unsigned32,
	wirelessIfTPC
		Unsigned32,
	wirelessIfCellSize
		INTEGER,
	wirelessIfDTIM
		Unsigned32,
	wirelessIfAntennaGain
		Unsigned32,
	wirelessIfCurrentActiveChannel
		Unsigned32,
	wirelessIfSatelliteDensity
		INTEGER,
	wirelessIfMPOperationalMode
		INTEGER,
	wirelessIfChannelWaitTime
		Unsigned32,
	wirelessIfActiveTPC
		Unsigned32,
	wirelessIfDfsNumSatWithRadarForFreqSwitch
		Unsigned32,
	wirelessIfDfsStatus
		INTEGER,
	wirelessIfTPC2
		DisplayString,
	wirelessIfActiveTPC2
		DisplayString,
	wirelessIfChannelOffset
		Integer32,
	wirelessIfATPCStatus
		INTEGER,
	wirelessIfATPCWaitInterval
		Unsigned32,
	wirelessIfATPCUpperMargin
		Unsigned32,
	wirelessIfATPCLowerMargin
		Unsigned32,
	wirelessIfATPCChangeInSteps
		Unsigned32,
	wirelessIfMaxEIRP
		Unsigned32,
	wirelessIfActiveEIRP
		DisplayString,
	wirelessIfActivePower
		DisplayString,
	wirelessIfAvailableChannels
		OCTET STRING,
	wirelessIfManualBlacklistModifier
		DisplayString,
	wirelessIfMaxTxPower
		DisplayString,
	wirelessIfTMPDCSStatus
		INTEGER,
	wirelessIfDCSReTxThreshold
		Integer32,
	wirelessIfDCSBadlinkThreshold
		Integer32,
	wirelessIfActiveChannelBandWidth
		DisplayString,
	wirelessIfActiveChannelOffset
		Integer32,
	wirelessIfSupportedChannelOffset
		DisplayString,
	wirelessIfActiveChannel
		DisplayString,
	wirelessIfWindowLength
		Unsigned32,
	wirelessIfSensitivity
		Unsigned32,
	wirelessIfSTBCStatus
		INTEGER,
	wirelessIfDFSFCC15407RuleStatus
		INTEGER,
	wirelessIfDFSCurrentFCCSpec
		DisplayString,
	wirelessIfOverwriteEeprom
		INTEGER,
	wirelessIfForcePreferredChannelStatus
		INTEGER,
	wirelessIfRFPlanningChannel
		Unsigned32,
	wirelessIfCurrentChannelLoad
		Integer32,
	wirelessIfOperationalLoadThreshold
		Unsigned32
}

wirelessIfPropertiesTableIndex  OBJECT-TYPE
	SYNTAX     Unsigned32 (1..2)
	MAX-ACCESS read-only
	STATUS     current
	DESCRIPTION 
		"This parameter represents a unique value for each Wireless interface 
		 in the system and is used as index to this table."
	::= { wirelessIfPropertiesTableEntry 1 }

wirelessIfPropertiesRadioStatus  OBJECT-TYPE
	SYNTAX     INTEGER {
		enable (1),
		disable (2)
	}
	MAX-ACCESS read-write
	STATUS     current
	DESCRIPTION 
		"This parameter is used to provide the status of the Wireless Radio 
		 interface. Select 
		 (1) to enable the wireless interface and 
		 (2) to disable the wireless interface.
		"
	DEFVAL  { enable }
	::= { wirelessIfPropertiesTableEntry 2 }

wirelessIfOperationalMode  OBJECT-TYPE
	SYNTAX     DisplayString (SIZE(1..128))
	MAX-ACCESS read-write
	STATUS     current
	DESCRIPTION 
		"This parameter is used to set the wireless NIC Operational mode.
		 Depending on the wireless NIC in the device different wireless
		 operational modes can be configured. The object wirelessIfSupportedOperationalMode
		                 shows the supported modes and the possible  supported modes for 
		                 AP products: 
		                   dot11b(1), 
		                  dot11g(2), 
		                  dot11ng(3), 
		                 dot11a(4), 
		                 dot11na(5)"
	::= { wirelessIfPropertiesTableEntry 3 }

wirelessIfSupportedOperationalMode  OBJECT-TYPE
	SYNTAX     DisplayString
	MAX-ACCESS read-only
	STATUS     current
	DESCRIPTION 
		"This parameter is used to set the wireless supported Operational mode."
	::= { wirelessIfPropertiesTableEntry 4 }

wirelessIfCurrentChannelBandwidth  OBJECT-TYPE
	SYNTAX     Unsigned32
	MAX-ACCESS read-write
	STATUS     current
	DESCRIPTION 
		"This parameter represents the current bandwidth that Wireless is 
		 currently operating on. It is represented in MHz"
	::= { wirelessIfPropertiesTableEntry 5 }

wirelessIfSupportedChannelBandwidth  OBJECT-TYPE
	SYNTAX     DisplayString
	MAX-ACCESS read-only
	STATUS     current
	DESCRIPTION 
		"This parameter represents the channel bandwidths that a wireless can support."
	::= { wirelessIfPropertiesTableEntry 6 }

wirelessIfAutoChannelSelection  OBJECT-TYPE
	SYNTAX     INTEGER {
		enable (1),
		disable (2)
	}
	MAX-ACCESS read-write
	STATUS     current
	DESCRIPTION 
		"This parameter is used to configure the auto channel selection for wireless 
		  interface. Select 
		  (1) to enable the auto channel selection and 
		  (2) to disable the auto channel selection. 
		"
	DEFVAL  { enable }
	::= { wirelessIfPropertiesTableEntry 7 }

wirelessIfCurrentOperatingChannel  OBJECT-TYPE
	SYNTAX     Unsigned32
	MAX-ACCESS read-write
	STATUS     current
	DESCRIPTION 
		"This parameter represents the user configured channel that the radio is 
		                 configured to operate in. 
		                 Note: It is possible that the currently active channel is different. 
		                       To find the current active/operational channel refer to 
		                       wirelessIfCurrentActiveChannel."
	::= { wirelessIfPropertiesTableEntry 8 }

wirelessIfSupportedChannels  OBJECT-TYPE
	SYNTAX     OCTET STRING (SIZE(0..1024))
	MAX-ACCESS read-only
	STATUS     current
	DESCRIPTION 
		"This parameter represents the channels that wireless can support. "
	::= { wirelessIfPropertiesTableEntry 9 }

wirelessIfAutoRateSelection  OBJECT-TYPE
	SYNTAX     INTEGER {
		enable (1),
		disable (2)
	}
	MAX-ACCESS read-write
	STATUS     current
	DESCRIPTION 
		"This parameter is used to configure the value for Auto Rate Selection for the 
		 wireless interface. Select  
		 (1) to enable the Auto Rate selection and 
		 (2) to disable the Auto Rate selection. 
		"
	DEFVAL  { enable }
	::= { wirelessIfPropertiesTableEntry 10 }

wirelessIfTransmittedRate  OBJECT-TYPE
	SYNTAX     Unsigned32 (0..255)
	MAX-ACCESS read-write
	STATUS     current
	DESCRIPTION 
		"This parameter represents the number of rates transmitted for wireless. "
	DEFVAL  { 0 }
	::= { wirelessIfPropertiesTableEntry 11 }

wirelessIfSupportedRate  OBJECT-TYPE
	SYNTAX     DisplayString
	MAX-ACCESS read-only
	STATUS     current
	DESCRIPTION 
		"This parameter represents the number of rates supported for wireless."
	::= { wirelessIfPropertiesTableEntry 12 }

wirelessIfVAPRTSThreshold  OBJECT-TYPE
	SYNTAX     Unsigned32 (1..2346)
	MAX-ACCESS read-write
	STATUS     current
	DESCRIPTION 
		"This parameter represents the maximum threshold for VAP RTS (Request To Send). 
		 The maximum threshold can be configured up to 2346. "
	DEFVAL  { 2346 }
	::= { wirelessIfPropertiesTableEntry 13 }

wirelessIfVAPBeaconInterval  OBJECT-TYPE
	SYNTAX     Unsigned32 (100..1000)
	MAX-ACCESS read-write
	STATUS     current
	DESCRIPTION 
		"This parameter represents the time interval that a beacon takes for getting 
		 transmitted for wireless VAP. By default, the value is set to 100 ms."
	DEFVAL  { 100 }
	::= { wirelessIfPropertiesTableEntry 14 }

wirelessIfTPC  OBJECT-TYPE
	SYNTAX     Unsigned32 (0..18)
	MAX-ACCESS read-write
	STATUS     deprecated
	DESCRIPTION 
		"This parameter represents the cell size that the transmitted power controls. It is 
		                 measured in dBm. Please check the wirelessIfActiveTPC for current active TPC."
	DEFVAL  { 0 }
	::= { wirelessIfPropertiesTableEntry 15 }

wirelessIfCellSize  OBJECT-TYPE
	SYNTAX     INTEGER {
		small (1),
		medium (2),
		large (3)
	}
	MAX-ACCESS read-write
	STATUS     deprecated
	DESCRIPTION 
		"This parameter represents the cell size of the wireless. By default, the cell size
		 is configured to large. Select 
		 (1) for Small cell size, 
		 (2) for Medium cell size and
		 (3) for Large cell size."
	DEFVAL  { large }
	::= { wirelessIfPropertiesTableEntry 16 }

wirelessIfDTIM  OBJECT-TYPE
	SYNTAX     Unsigned32 (1..255)
	MAX-ACCESS read-write
	STATUS     current
	DESCRIPTION 
		"This parameter represents the delivery traffic indication map  
		         period.  This is the interval between the transmission of multicast 
		         frames on the wireless inteface.  It is expressed in the Beacon 
		         messages. The recommended default value for this parameter is 1."
	DEFVAL  { 1 }
	::= { wirelessIfPropertiesTableEntry 17 }

wirelessIfAntennaGain  OBJECT-TYPE
	SYNTAX     Unsigned32 (0..40)
	MAX-ACCESS read-write
	STATUS     current
	DESCRIPTION 
		"This parameter is used to configure the antenna gain."
	DEFVAL  { 0 }
	::= { wirelessIfPropertiesTableEntry 18 }

wirelessIfCurrentActiveChannel  OBJECT-TYPE
	SYNTAX     Unsigned32
	MAX-ACCESS read-only
	STATUS     deprecated
	DESCRIPTION 
		"This parameter represents the current active channel that wireless radio is 
		                 operating on. It may be different from the configured channel represented by
		                 wirelessIfCurrentOperatingChannel."
	::= { wirelessIfPropertiesTableEntry 19 }

wirelessIfSatelliteDensity  OBJECT-TYPE
	SYNTAX     INTEGER {
		disable (1),
		large (2),
		medium (3),
		small (4),
		mini (5),
		micro (6)
	}
	MAX-ACCESS read-write
	STATUS     current
	DESCRIPTION 
		"This parameter represents the density of the satellites for the BSU.
		                 It configures the BSU to accomodate the satellites for the specified 
		                 range."
	::= { wirelessIfPropertiesTableEntry 20 }

wirelessIfMPOperationalMode  OBJECT-TYPE
	SYNTAX     INTEGER {
		highThroughput (1),
		legacy (2)
	}
	MAX-ACCESS read-write
	STATUS     current
	DESCRIPTION 
		"This parameter is used to set the wireless NIC Operational mode for Tsunami Multi
		                      Point Products."
	::= { wirelessIfPropertiesTableEntry 21 }

wirelessIfChannelWaitTime  OBJECT-TYPE
	SYNTAX     Unsigned32 (60..3600)
	MAX-ACCESS read-write
	STATUS     current
	DESCRIPTION 
		"This parameter is used to configure the DFS channel wait time."
	DEFVAL  { 60 }
	::= { wirelessIfPropertiesTableEntry 22 }

wirelessIfActiveTPC  OBJECT-TYPE
	SYNTAX     Unsigned32 (0..18)
	MAX-ACCESS read-only
	STATUS     deprecated
	DESCRIPTION 
		"This parameter shows the active cell size that the transmitted power controls. It is
		                 measured in dBm"
	::= { wirelessIfPropertiesTableEntry 23 }

wirelessIfDfsNumSatWithRadarForFreqSwitch  OBJECT-TYPE
	SYNTAX     Unsigned32 (0..250)
	MAX-ACCESS read-write
	STATUS     current
	DESCRIPTION 
		"This parameter represents the minimum number of satellites reporting RADAR for BSU to 
		                 switch to a new best channel/frequency. The default value is (0) that indicates BSU to never switch to a 
		                 new best channel/frequency for any number of satellites reporting RADAR."
	DEFVAL  { 0 }
	::= { wirelessIfPropertiesTableEntry 24 }

wirelessIfDfsStatus  OBJECT-TYPE
	SYNTAX     INTEGER {
		enable (1),
		disable (2)
	}
	MAX-ACCESS read-write
	STATUS     current
	DESCRIPTION 
		"This parameter is used to configure the status of the DFS for SU. Configuring this parameter 
		for BSU will not affecte BSU Status. 
		 1 to enable the DFS, 
		 2 to disable the DFS."
	DEFVAL  { disable }
	::= { wirelessIfPropertiesTableEntry 25 }

wirelessIfTPC2  OBJECT-TYPE
	SYNTAX     DisplayString (SIZE(1..5))
	MAX-ACCESS read-write
	STATUS     deprecated
	DESCRIPTION 
		"This parameter represents the transmitted power control. It is measured in dBm.
		                This is now deprecated. Instead use linkProfileTPC."
	::= { wirelessIfPropertiesTableEntry 26 }

wirelessIfActiveTPC2  OBJECT-TYPE
	SYNTAX     DisplayString (SIZE(1..5))
	MAX-ACCESS read-only
	STATUS     deprecated
	DESCRIPTION 
		"This parameter shows the active TPC(Transmitted power control) applied when ATPC is enabled. It is
		                 measured in dBm. This is now deprecated."
	::= { wirelessIfPropertiesTableEntry 27 }

wirelessIfChannelOffset  OBJECT-TYPE
	SYNTAX     Integer32 (-2..2)
	MAX-ACCESS read-write
	STATUS     current
	DESCRIPTION 
		"This parameter is used to shift the channel center frequency."
	DEFVAL  { 0 }
	::= { wirelessIfPropertiesTableEntry 31 }

wirelessIfATPCStatus  OBJECT-TYPE
	SYNTAX     INTEGER {
		enable (1),
		disable (2)
	}
	MAX-ACCESS read-write
	STATUS     deprecated
	DESCRIPTION 
		"This parameter is used to enable or disable the ATPC feature.
		        This is now deprecated. Instead use linkProfileATPCStatus."
	::= { wirelessIfPropertiesTableEntry 32 }

wirelessIfATPCWaitInterval  OBJECT-TYPE
	SYNTAX     Unsigned32
	MAX-ACCESS read-write
	STATUS     deprecated
	DESCRIPTION 
		"ATPC wait interval is amount of time algorithm will wait after applying TPC. 
		        Next check will be done only after this interval. 
		        This gives enough time for SNR to settle down, after applying TPC.
		        This is now deprecated."
	::= { wirelessIfPropertiesTableEntry 33 }

wirelessIfATPCUpperMargin  OBJECT-TYPE
	SYNTAX     Unsigned32 (0..20)
	MAX-ACCESS read-write
	STATUS     deprecated
	DESCRIPTION 
		"This parameter will added to actual threshold and only if the current SNR is above 
		        this threshold the TPC will be incremented. This is now deprecated.
		        Instead use linkProfileATPCUpperMargin."
	::= { wirelessIfPropertiesTableEntry 34 }

wirelessIfATPCLowerMargin  OBJECT-TYPE
	SYNTAX     Unsigned32 (0..20)
	MAX-ACCESS read-write
	STATUS     deprecated
	DESCRIPTION 
		"This parameter will decremented from actual threshold and only if the current SNR is 
		        below this threshold the TPC will be decremented. This is now deprecated.
		        Instead use linkProfileATPCLowerMargin."
	::= { wirelessIfPropertiesTableEntry 35 }

wirelessIfATPCChangeInSteps  OBJECT-TYPE
	SYNTAX     Unsigned32 (1..15)
	MAX-ACCESS read-write
	STATUS     deprecated
	DESCRIPTION 
		"Increment or decrement of TPC will be done in steps of ATPC change in steps."
	::= { wirelessIfPropertiesTableEntry 36 }

wirelessIfMaxEIRP  OBJECT-TYPE
	SYNTAX     Unsigned32 (0..100)
	MAX-ACCESS read-write
	STATUS     current
	DESCRIPTION 
		"Maximum effective power should be radiated from the antenna. Default value will 
		                 change based on country code."
	::= { wirelessIfPropertiesTableEntry 37 }

wirelessIfActiveEIRP  OBJECT-TYPE
	SYNTAX     DisplayString
	MAX-ACCESS read-only
	STATUS     deprecated
	DESCRIPTION 
		"Active EIRP will show current EIRP at any instance. This is now deprecated."
	::= { wirelessIfPropertiesTableEntry 38 }

wirelessIfActivePower  OBJECT-TYPE
	SYNTAX     DisplayString
	MAX-ACCESS read-only
	STATUS     deprecated
	DESCRIPTION 
		"Active Power will show current radio tx power at any instance. This is now deprecated."
	::= { wirelessIfPropertiesTableEntry 39 }

wirelessIfAvailableChannels  OBJECT-TYPE
	SYNTAX     OCTET STRING (SIZE(0..1024))
	MAX-ACCESS read-only
	STATUS     deprecated
	DESCRIPTION 
		""
	::= { wirelessIfPropertiesTableEntry 40 }

wirelessIfManualBlacklistModifier  OBJECT-TYPE
	SYNTAX     DisplayString
	MAX-ACCESS read-write
	STATUS     deprecated
	DESCRIPTION 
		""
	::= { wirelessIfPropertiesTableEntry 41 }

wirelessIfMaxTxPower  OBJECT-TYPE
	SYNTAX     DisplayString
	MAX-ACCESS read-only
	STATUS     current
	DESCRIPTION 
		"This parameter is used to display max tx power.
		 Obtained value divided by 2 gives max tx power."
	::= { wirelessIfPropertiesTableEntry 42 }

wirelessIfTMPDCSStatus  OBJECT-TYPE
	SYNTAX     INTEGER {
		enable (1),
		disable (2)
	}
	MAX-ACCESS read-write
	STATUS     current
	DESCRIPTION 
		"This parameter is used to enable or disable the DCS Feature
		                         This configuration is valid only on BSU."
	DEFVAL  { disable }
	::= { wirelessIfPropertiesTableEntry 43 }

wirelessIfDCSReTxThreshold  OBJECT-TYPE
	SYNTAX     Integer32 (1..100)
	MAX-ACCESS read-write
	STATUS     current
	DESCRIPTION 
		"This parameter represents DCS ReTransmission Threshold."
	DEFVAL  { 50 }
	::= { wirelessIfPropertiesTableEntry 44 }

wirelessIfDCSBadlinkThreshold  OBJECT-TYPE
	SYNTAX     Integer32 (1..250)
	MAX-ACCESS read-write
	STATUS     current
	DESCRIPTION 
		"This parameter configure  DCS Satellite Number."
	DEFVAL  { 1 }
	::= { wirelessIfPropertiesTableEntry 45 }

wirelessIfActiveChannelBandWidth  OBJECT-TYPE
	SYNTAX     DisplayString
	MAX-ACCESS read-only
	STATUS     current
	DESCRIPTION 
		""
	::= { wirelessIfPropertiesTableEntry 46 }

wirelessIfActiveChannelOffset  OBJECT-TYPE
	SYNTAX     Integer32 (-2..2)
	MAX-ACCESS read-only
	STATUS     current
	DESCRIPTION 
		""
	::= { wirelessIfPropertiesTableEntry 47 }

wirelessIfSupportedChannelOffset  OBJECT-TYPE
	SYNTAX     DisplayString
	MAX-ACCESS read-only
	STATUS     current
	DESCRIPTION 
		"This parameter is used to display the supported channel offsets."
	::= { wirelessIfPropertiesTableEntry 48 }

wirelessIfActiveChannel  OBJECT-TYPE
	SYNTAX     DisplayString
	MAX-ACCESS read-only
	STATUS     current
	DESCRIPTION 
		"This parameter is used to display the Active channel."
	::= { wirelessIfPropertiesTableEntry 49 }

wirelessIfWindowLength  OBJECT-TYPE
	SYNTAX     Unsigned32 (0..3)
	MAX-ACCESS read-write
	STATUS     current
	DESCRIPTION 
		"This parameter is used to configure window length."
	::= { wirelessIfPropertiesTableEntry 50 }

wirelessIfSensitivity  OBJECT-TYPE
	SYNTAX     Unsigned32 (0..63)
	MAX-ACCESS read-write
	STATUS     current
	DESCRIPTION 
		"This parameter is used to configure sensitivity."
	::= { wirelessIfPropertiesTableEntry 51 }

wirelessIfSTBCStatus  OBJECT-TYPE
	SYNTAX     INTEGER {
		enable (1),
		disable (2)
	}
	MAX-ACCESS read-write
	STATUS     current
	DESCRIPTION 
		"This parameter is used to configure the value for Space Time Block Code for the 
		 wireless interface. Select  
		 (1) to enable the STBC and 
		 (2) to disable the STBC."
	DEFVAL  { disable }
	::= { wirelessIfPropertiesTableEntry 52 }

wirelessIfDFSFCC15407RuleStatus  OBJECT-TYPE
	SYNTAX     INTEGER {
		enable (1),
		disable (2)
	}
	MAX-ACCESS read-write
	STATUS     current
	DESCRIPTION 
		"This parameter is used to configure the DFS FCC15407 Rule Status.Select  
		 (1) to enable the DFS FCC15407 Rule and 
		 (2) to disable the DFS FCC15407 Rule."
	DEFVAL  { disable }
	::= { wirelessIfPropertiesTableEntry 53 }

wirelessIfDFSCurrentFCCSpec  OBJECT-TYPE
	SYNTAX     DisplayString (SIZE(0..255))
	MAX-ACCESS read-only
	STATUS     current
	DESCRIPTION 
		"This parameter is used to Display the DFS Current FCC Spec."
	::= { wirelessIfPropertiesTableEntry 54 }

wirelessIfOverwriteEeprom  OBJECT-TYPE
	SYNTAX     INTEGER {
		enable (1),
		disable (2)
	}
	MAX-ACCESS read-write
	STATUS     current
	DESCRIPTION 
		"This parameter is used to overwrite Eeprom"
	DEFVAL  { disable }
	::= { wirelessIfPropertiesTableEntry 55 }

wirelessIfForcePreferredChannelStatus  OBJECT-TYPE
	SYNTAX     INTEGER {
		enable (1),
		disable (2)
	}
	MAX-ACCESS read-write
	STATUS     current
	DESCRIPTION 
		"This parameter is used to enable/disable the use of preferred channel after deblacklist"
	DEFVAL  { enable }
	::= { wirelessIfPropertiesTableEntry 56 }

wirelessIfRFPlanningChannel  OBJECT-TYPE
	SYNTAX     Unsigned32
	MAX-ACCESS read-write
	STATUS     current
	DESCRIPTION 
		"This parameter is used by PVADV to configure all devices in same channel while channel planning."
	::= { wirelessIfPropertiesTableEntry 57 }

wirelessIfCurrentChannelLoad  OBJECT-TYPE
	SYNTAX     Integer32
	MAX-ACCESS read-only
	STATUS     current
	DESCRIPTION 
		""
	::= { wirelessIfPropertiesTableEntry 58 }

wirelessIfOperationalLoadThreshold  OBJECT-TYPE
	SYNTAX     Unsigned32 (0..100)
	MAX-ACCESS read-write
	STATUS     current
	DESCRIPTION 
		""
	DEFVAL  { 90 }
	::= { wirelessIfPropertiesTableEntry 59 }


-- Wireless Interface 11n properties Table

wirelessIf11nPropertiesTable  OBJECT-TYPE
	SYNTAX SEQUENCE OF WirelessIf11nPropertiesTableEntry
	MAX-ACCESS not-accessible
	STATUS     current
	DESCRIPTION 
		"This table holds the wireless11n configurations."
	::= { wirelessIf 2 }

wirelessIf11nPropertiesTableEntry  OBJECT-TYPE
	SYNTAX 	WirelessIf11nPropertiesTableEntry
	MAX-ACCESS not-accessible
	STATUS     current
	DESCRIPTION 
		"This parameter represents the entry for wireless11n properties table."
	INDEX { wirelessIf11nPropertiesTableIndex }
	::= { wirelessIf11nPropertiesTable 1 }

WirelessIf11nPropertiesTableEntry ::= SEQUENCE {
	wirelessIf11nPropertiesTableIndex
		Unsigned32,
	wirelessIf11nPropertiesAMPDUStatus
		INTEGER,
	wirelessIf11nPropertiesAMPDUMaxNumFrames
		Unsigned32,
	wirelessIf11nPropertiesAMPDUMaxFrameSize
		Unsigned32,
	wirelessIf11nPropertiesAMSDUStatus
		INTEGER,
	wirelessIf11nPropertiesAMSDUMaxFrameSize
		Unsigned32,
	wirelessIf11nPropertiesFrequencyExtension
		INTEGER,
	wirelessIf11nPropertiesGuardInterval
		INTEGER,
	wirelessIf11nPropertiesTxAntennas
		INTEGER,
	wirelessIf11nPropertiesRxAntennas
		INTEGER,
	wirelessIf11nPropertiesNumOfSpatialStreams
		INTEGER,
	wirelessIf11nPropertiesSupportedTxAntennas
		DisplayString,
	wirelessIf11nPropertiesSupportedRxAntennas
		DisplayString
}

wirelessIf11nPropertiesTableIndex  OBJECT-TYPE
	SYNTAX     Unsigned32 (1..2)
	MAX-ACCESS read-only
	STATUS     current
	DESCRIPTION 
		"This parameter represents index to the wireless interface 11n
		 table and this represents the wireless radios."
	::= { wirelessIf11nPropertiesTableEntry 1 }

wirelessIf11nPropertiesAMPDUStatus  OBJECT-TYPE
	SYNTAX     INTEGER {
		enable (1),
		disable (2)
	}
	MAX-ACCESS read-write
	STATUS     current
	DESCRIPTION 
		"This parameter is used define the AMPDU status for wireless 11n 
		 interface. Select 
		  1 to enable and 
		  2 to disable the AMPDU status."
	::= { wirelessIf11nPropertiesTableEntry 2 }

wirelessIf11nPropertiesAMPDUMaxNumFrames  OBJECT-TYPE
	SYNTAX     Unsigned32 (1..64)
	MAX-ACCESS read-write
	STATUS     current
	DESCRIPTION 
		"This parameter represents the Agregated MAC Protocol Data Unit 
		 (AMPDU) frames that are transmitted. It can be configured up to 64 frames."
	DEFVAL  { 64 }
	::= { wirelessIf11nPropertiesTableEntry 3 }

wirelessIf11nPropertiesAMPDUMaxFrameSize  OBJECT-TYPE
	SYNTAX     Unsigned32 (1024..65535)
	MAX-ACCESS read-write
	STATUS     current
	DESCRIPTION 
		"This parameter is used to configure the maximum AMPDU frame size 
		 (in bytes) that can be transmitted."
	DEFVAL  { 65535 }
	::= { wirelessIf11nPropertiesTableEntry 4 }

wirelessIf11nPropertiesAMSDUStatus  OBJECT-TYPE
	SYNTAX     INTEGER {
		enable (1),
		disable (2)
	}
	MAX-ACCESS read-write
	STATUS     current
	DESCRIPTION 
		"This parameter is used define the AMSDU status for wireless 11n 
		 interface. Select 
		 1 to enable and 
		 2 to disable the AMSDU status."
	::= { wirelessIf11nPropertiesTableEntry 5 }

wirelessIf11nPropertiesAMSDUMaxFrameSize  OBJECT-TYPE
	SYNTAX     Unsigned32 (4096)
	MAX-ACCESS read-only
	STATUS     current
	DESCRIPTION 
		"This parameter shows the maximum AMSDU frame size 
		 (in bytes) that can be transmitted."
	::= { wirelessIf11nPropertiesTableEntry 6 }

wirelessIf11nPropertiesFrequencyExtension  OBJECT-TYPE
	SYNTAX     INTEGER {
		upperExtensionChannel (1),
		lowerExtensionChannel (2)
	}
	MAX-ACCESS read-write
	STATUS     current
	DESCRIPTION 
		"This parameter is used to configure the frequency extension for 
		 the wireless interface. Select 
		 1 to configure the UpperExtensionChannel and
		 2 to configure the LowerExtensionChannel."
	DEFVAL  { upperExtensionChannel }
	::= { wirelessIf11nPropertiesTableEntry 7 }

wirelessIf11nPropertiesGuardInterval  OBJECT-TYPE
	SYNTAX     INTEGER {
		shortGI-400nSec (1),
		fullGI-800nSec (2)
	}
	MAX-ACCESS read-write
	STATUS     current
	DESCRIPTION 
		"This parameter is used to configure the guard interval for the
		 wireless interface. Select 1 for short guard interval as 400 
		 nano seconds and 2 for full guard interval as 800 nano seconds."
	DEFVAL  { fullGI-800nSec }
	::= { wirelessIf11nPropertiesTableEntry 8 }

wirelessIf11nPropertiesTxAntennas  OBJECT-TYPE
	SYNTAX     INTEGER {
		one (1),
		two (2),
		three (3),
		four (4),
		five (5),
		six (6),
		seven (7)
	}
	MAX-ACCESS read-write
	STATUS     deprecated
	DESCRIPTION 
		"This parameter enables the transmission antennas. This is configured 
		 as bit-mask.
		 Eg: 3 - 011 (binary value) - first and second antennas are enabled.
		     7 - 111 (binary value) - all three are enabled.
		         This is now deprecated. Instead use linkProfileTxAntChainMask."
	DEFVAL  { seven }
	::= { wirelessIf11nPropertiesTableEntry 9 }

wirelessIf11nPropertiesRxAntennas  OBJECT-TYPE
	SYNTAX     INTEGER {
		one (1),
		two (2),
		three (3),
		four (4),
		five (5),
		six (6),
		seven (7)
	}
	MAX-ACCESS read-write
	STATUS     current
	DESCRIPTION 
		"This parameter enables the receiving antennas. This is configured 
		 as bit-mask.
		 Eg: 3 - 011 (binary value) - first and second antennas are enabled.
		     7 - 111 (binary value) - all three are enabled."
	DEFVAL  { seven }
	::= { wirelessIf11nPropertiesTableEntry 10 }

wirelessIf11nPropertiesNumOfSpatialStreams  OBJECT-TYPE
	SYNTAX     INTEGER {
		single (1),
		dual (2),
		auto (3)
	}
	MAX-ACCESS read-write
	STATUS     deprecated
	DESCRIPTION 
		"This parameter is used to select the number of spatial streams for 11n.
		        This is now deprecated. Instead use linkProfileDataStreams."
	DEFVAL  { single }
	::= { wirelessIf11nPropertiesTableEntry 11 }

wirelessIf11nPropertiesSupportedTxAntennas  OBJECT-TYPE
	SYNTAX     DisplayString (SIZE(1..64))
	MAX-ACCESS read-only
	STATUS     deprecated
	DESCRIPTION 
		"This parameter shows the number of supported Tx antennas.
		        This is now deprecated. Instead use linkProfileSupportedTxAntChainMask."
	::= { wirelessIf11nPropertiesTableEntry 12 }

wirelessIf11nPropertiesSupportedRxAntennas  OBJECT-TYPE
	SYNTAX     DisplayString (SIZE(1..64))
	MAX-ACCESS read-only
	STATUS     current
	DESCRIPTION 
		"This parameter shows the number of supported Rx antennas."
	::= { wirelessIf11nPropertiesTableEntry 13 }

-- Wireless Interface VAP Table

wirelessIfVAPTable  OBJECT-TYPE
	SYNTAX SEQUENCE OF WirelessIfVAPTableEntry
	MAX-ACCESS not-accessible
	STATUS     current
	DESCRIPTION 
		"This table holds the wireless VAP (virtual access point) configurations."
	::= { wirelessIf 3 }

wirelessIfVAPTableEntry  OBJECT-TYPE
	SYNTAX 	WirelessIfVAPTableEntry
	MAX-ACCESS not-accessible
	STATUS     current
	DESCRIPTION 
		"This parameter represents the entry for the wireless VAP table."
	INDEX { wirelessIfVAPTableIndex, 
		wirelessIfVAPTableSecIndex }
	::= { wirelessIfVAPTable 1 }

WirelessIfVAPTableEntry ::= SEQUENCE {
	wirelessIfVAPTableIndex
		Unsigned32,
	wirelessIfVAPTableSecIndex
		Unsigned32,
	wirelessIfVAPType
		INTEGER,
	wirelessIfVAPSSID
		DisplayString,
	wirelessIfVAPBSSID
		MacAddress,
	wirelessIfVAPBroadcastSSID
		INTEGER,
	wirelessIfVAPFragmentationThreshold
		Unsigned32,
	wirelessIfVAPSecurityProfileName
		DisplayString,
	wirelessIfVAPRadiusProfileName
		DisplayString,
	wirelessIfVAPVLANID
		VlanId,
	wirelessIfVAPVLANPriority
		Unsigned32,
	wirelessIfVAPQoSProfileName
		DisplayString,
	wirelessIfVAPMACACLStatus
		INTEGER,
	wirelessIfVAPRadiusMACACLStatus
		INTEGER,
	wirelessIfVAPRadiusAccStatus
		INTEGER,
	wirelessIfVAPStatus
		INTEGER
}

wirelessIfVAPTableIndex  OBJECT-TYPE
	SYNTAX     Unsigned32 (1..2)
	MAX-ACCESS read-only
	STATUS     current
	DESCRIPTION 
		"This parameter is used to configure the wireless VAP table.  Select 
		 1 represents Wifi0 (radio-0) and 
		 2 represents Wifi1 (radio-1)."
	::= { wirelessIfVAPTableEntry 1 }

wirelessIfVAPTableSecIndex  OBJECT-TYPE
	SYNTAX     Unsigned32 (1..4)
	MAX-ACCESS read-only
	STATUS     current
	DESCRIPTION 
		"This parameter represents the VAPs and used as secondary index to this 
		                 table."
	::= { wirelessIfVAPTableEntry 2 }

wirelessIfVAPType  OBJECT-TYPE
	SYNTAX     INTEGER {
		ap (1)
	}
	MAX-ACCESS read-write
	STATUS     current
	DESCRIPTION 
		"This parameter is used to configure the type of VAP. Select 
		 1 for AP."
	DEFVAL  { ap }
	::= { wirelessIfVAPTableEntry 3 }

wirelessIfVAPSSID  OBJECT-TYPE
	SYNTAX     DisplayString (SIZE(1..32))
	MAX-ACCESS read-write
	STATUS     current
	DESCRIPTION 
		"This parameter is used to represent the wireless card SSID name
		 (wireless network name)."
	::= { wirelessIfVAPTableEntry 4 }

wirelessIfVAPBSSID  OBJECT-TYPE
	SYNTAX     MacAddress
	MAX-ACCESS read-only
	STATUS     current
	DESCRIPTION 
		"This parameter represents the MAC address for the VAP BSSID. "
	::= { wirelessIfVAPTableEntry 5 }

wirelessIfVAPBroadcastSSID  OBJECT-TYPE
	SYNTAX     INTEGER {
		enable (1),
		disable (2)
	}
	MAX-ACCESS read-write
	STATUS     current
	DESCRIPTION 
		"This parameter is used to configure the status of the broadcast 
		 wireless VAP SSID. A single entry in the SSID table can be enabled
		 to broadcast SSID in beacon messages.
		 Select 
		 1 to enable, 
		 2 to disable"
	DEFVAL  { enable }
	::= { wirelessIfVAPTableEntry 6 }

wirelessIfVAPFragmentationThreshold  OBJECT-TYPE
	SYNTAX     Unsigned32 (256..2346)
	MAX-ACCESS read-write
	STATUS     current
	DESCRIPTION 
		"This parameter is used to configure the fragmentation threshold 
		 for the wireless VAP. By default, the value is set to 2346."
	DEFVAL  { 2346 }
	::= { wirelessIfVAPTableEntry 7 }

wirelessIfVAPSecurityProfileName  OBJECT-TYPE
	SYNTAX     DisplayString (SIZE(1..32))
	MAX-ACCESS read-write
	STATUS     current
	DESCRIPTION 
		"This parameter allows you to configure the Security profile name 
		 for Wireless VAP."
	::= { wirelessIfVAPTableEntry 8 }

wirelessIfVAPRadiusProfileName  OBJECT-TYPE
	SYNTAX     DisplayString (SIZE(1..32))
	MAX-ACCESS read-write
	STATUS     current
	DESCRIPTION 
		"This parameter allows you to configure the RADIUS profile name for 
		 Wireless VAP."
	::= { wirelessIfVAPTableEntry 9 }

wirelessIfVAPVLANID  OBJECT-TYPE
	SYNTAX     VlanId
	MAX-ACCESS read-write
	STATUS     current
	DESCRIPTION 
		"This parameter is used to represent the VLAN ID for the wireless VAP.
		 Select any value between 1 - 4094 to tag the VLAN ids and -1 to untag
		 the VLAN ids."
	DEFVAL  { -1 }
	::= { wirelessIfVAPTableEntry 10 }

wirelessIfVAPVLANPriority  OBJECT-TYPE
	SYNTAX     Unsigned32 (0..7)
	MAX-ACCESS read-write
	STATUS     current
	DESCRIPTION 
		"This parameter is used to configure the VLAN priority for Wireless VAP. 
		 By default the value is set to 0."
	DEFVAL  { 0 }
	::= { wirelessIfVAPTableEntry 11 }

wirelessIfVAPQoSProfileName  OBJECT-TYPE
	SYNTAX     DisplayString (SIZE(1..32))
	MAX-ACCESS read-write
	STATUS     current
	DESCRIPTION 
		"This parameter is used to configure the profile name for the Wireless VAP QoS."
	::= { wirelessIfVAPTableEntry 12 }

wirelessIfVAPMACACLStatus  OBJECT-TYPE
	SYNTAX     INTEGER {
		enable (1),
		disable (2)
	}
	MAX-ACCESS read-write
	STATUS     current
	DESCRIPTION 
		"This parameter is used to enable or disable the MAC access control list."
	DEFVAL  { disable }
	::= { wirelessIfVAPTableEntry 13 }

wirelessIfVAPRadiusMACACLStatus  OBJECT-TYPE
	SYNTAX     INTEGER {
		enable (1),
		disable (2)
	}
	MAX-ACCESS read-write
	STATUS     current
	DESCRIPTION 
		"This parameter is used to enable or disable the MAC ACL for Radius Profiles"
	DEFVAL  { disable }
	::= { wirelessIfVAPTableEntry 14 }

wirelessIfVAPRadiusAccStatus  OBJECT-TYPE
	SYNTAX     INTEGER {
		enable (1),
		disable (2)
	}
	MAX-ACCESS read-write
	STATUS     current
	DESCRIPTION 
		"This parameter is used to enable or disable the Radius Accounting Stats capture."
	DEFVAL  { disable }
	::= { wirelessIfVAPTableEntry 15 }

wirelessIfVAPStatus  OBJECT-TYPE
	SYNTAX     INTEGER {
		enable (1),
		disable (2),
		delete (3)
	}
	MAX-ACCESS read-write
	STATUS     current
	DESCRIPTION 
		"This parameter is used to configure the status of the VAP. Select 
		 1 to enable the VAP, 
		 2 to disable the VAP and 
		 3 to delete the VAP."
	DEFVAL  { enable }
	::= { wirelessIfVAPTableEntry 16 }

-- Wireless Interface WORP Table

wirelessIfWORPTable  OBJECT-TYPE
	SYNTAX SEQUENCE OF WirelessIfWORPTableEntry
	MAX-ACCESS not-accessible
	STATUS     current
	DESCRIPTION 
		"This table holds the wireless WORP protocol configurations"
	::= { wirelessIf 4 }

wirelessIfWORPTableEntry  OBJECT-TYPE
	SYNTAX 	WirelessIfWORPTableEntry
	MAX-ACCESS not-accessible
	STATUS     current
	DESCRIPTION 
		"This object represents the entry for the wireless WORP table"
	INDEX { wirelessIfWORPTableIndex }
	::= { wirelessIfWORPTable 1 }

WirelessIfWORPTableEntry ::= SEQUENCE {
	wirelessIfWORPTableIndex
		Unsigned32,
	wirelessIfWORPMode
		DisplayString,
	wirelessIfWORPBaseStationName
		DisplayString,
	wirelessIfWORPNetworkName
		DisplayString,
	wirelessIfWORPMaxSatellites
		Unsigned32,
	wirelessIfWORPMTU
		Unsigned32,
	wirelessIfWORPSuperPacketing
		INTEGER,
	wirelessIfWORPSleepMode
		INTEGER,
	wirelessIfWORPMultiFrameBursting
		INTEGER,
	wirelessIfWORPRegistrationTimeout
		Unsigned32,
	wirelessIfWORPRetries
		Unsigned32,
	wirelessIfWORPTxRate
		Unsigned32,
	wirelessIfWORPSupportedTxRate
		DisplayString,
	wirelessIfWORPInputBandwidthLimit
		Unsigned32,
	wirelessIfWORPOutputBandwidthLimit
		Unsigned32,
	wirelessIfWORPBandwidthLimitType
		INTEGER,
	wirelessIfWORPSecurityProfileIndex
		INTEGER,
	wirelessIfWORPRadiusProfileIndex
		INTEGER,
	wirelessIfWORPMACACLStatus
		INTEGER,
	wirelessIfWORPRadiusMACACLStatus
		INTEGER,
	wirelessIfWORPRadiusAccStatus
		INTEGER,
	wirelessIfWORPIntfMacAddress
		MacAddress,
	wirelessIfWORPAutoMultiFrameBursting
		INTEGER,
	wirelessIfWORPMaxTimedOutSatellites
		Integer32,
	wirelessIfWORPErrorCountThreshold
		Integer32,
	wirelessIfWORPRSSIDropThreshold
		Integer32,
	wirelessIfWORPSecBaseStationName
		DisplayString,
	wirelessIfWORPBaseSwitchInterval
		Integer32,
	wirelessIfWORPSyncStatus
		INTEGER,
	wirelessIfWORPSyncDLTimeFrame
		Unsigned32,
	wirelessIfWORPSyncULTimeFrame
		Unsigned32,
	wirelessIfWORPSyncInterFrameDelay
		Unsigned32,
	wirelessIfWORPSyncIntraFrameDelay
		Unsigned32,
	wirelessIfWORPSyncOffset
		Integer32,
	wirelessIfWORPSyncStopIfNoGPS
		INTEGER,
	wirelessIfWORPSyncDLSubSlots
		Unsigned32,
	wirelessIfWORPSyncULSubSlots
		Unsigned32,
	wirelessIfWORPSyncCompatibility
		INTEGER,
	wirelessIfWORPSyncDLRatio
		Unsigned32,
	wirelessIfWORPSyncMaxDistance
		Unsigned32,
	wirelessIfWORPSyncControlSlots
		Unsigned32,
	wirelessIfWORPSyncGPSSource
		INTEGER,
	wirelessIfWORPMinRSSIThrld
		Unsigned32,
	wirelessIfWORPMinRSSIThrldOffset
		Unsigned32,
	wirelessIfWORPLinkInactivityTimer
		Unsigned32,
	wirelessIfWORPDisconnectionInterval
		Unsigned32,
	wirelessIfWORPTimeoutOffset
		Unsigned32
}

wirelessIfWORPTableIndex  OBJECT-TYPE
	SYNTAX     Unsigned32 (1..2)
	MAX-ACCESS read-only
	STATUS     current
	DESCRIPTION 
		"This parameter represents the radio for which the WORP is enabled
		                 and index to the wirelessIfWORPTable."
	::= { wirelessIfWORPTableEntry 1 }

wirelessIfWORPMode  OBJECT-TYPE
	SYNTAX     DisplayString
	MAX-ACCESS read-only
	STATUS     current
	DESCRIPTION 
		"This parameter displays the worp mode of operation."
	::= { wirelessIfWORPTableEntry 2 }

wirelessIfWORPBaseStationName  OBJECT-TYPE
	SYNTAX     DisplayString (SIZE(0..32))
	MAX-ACCESS read-write
	STATUS     current
	DESCRIPTION 
		"This parameter represents the name of the BSU for which it can 
		                 register. This configuration is valid only on SU. If this 
		                 field is empty then SU is allowed to register with any BSU."
	::= { wirelessIfWORPTableEntry 3 }

wirelessIfWORPNetworkName  OBJECT-TYPE
	SYNTAX     DisplayString (SIZE(1..32))
	MAX-ACCESS read-write
	STATUS     current
	DESCRIPTION 
		"This parameter represents the name of the Network of the WORP Interface."
	::= { wirelessIfWORPTableEntry 4 }

wirelessIfWORPMaxSatellites  OBJECT-TYPE
	SYNTAX     Unsigned32 (1..250)
	MAX-ACCESS read-write
	STATUS     current
	DESCRIPTION 
		"This parameter represents the maximum number of SUs allowed to register on
		                 this BSU. This configuration is valid only on BSU."
	DEFVAL  { 100 }
	::= { wirelessIfWORPTableEntry 5 }

wirelessIfWORPMTU  OBJECT-TYPE
	SYNTAX     Unsigned32 (350..3808)
	MAX-ACCESS read-write
	STATUS     current
	DESCRIPTION 
		"This parameter represents to maximum size of a frame sent from the WORP interface."
	DEFVAL  { 3808 }
	::= { wirelessIfWORPTableEntry 6 }

wirelessIfWORPSuperPacketing  OBJECT-TYPE
	SYNTAX     INTEGER {
		enable (1),
		disable (2)
	}
	MAX-ACCESS read-write
	STATUS     current
	DESCRIPTION 
		"This parameter represents the status of bundling multiple ethernet frames in one
		                 single WORP Jumbo frame"
	DEFVAL  { enable }
	::= { wirelessIfWORPTableEntry 7 }

wirelessIfWORPSleepMode  OBJECT-TYPE
	SYNTAX     INTEGER {
		enable (1),
		disable (2)
	}
	MAX-ACCESS read-write
	STATUS     current
	DESCRIPTION 
		"This parameter represents the status of sleep mode. This Configuration is valid 
		                 only on BSU. If there is no data available to transfer b/w BSU & SU,  BSU 
		                 will keep the SU state in sleep state and polls that particular SU for every
		                 4 seconds to just to maintain the WORP link. "
	DEFVAL  { enable }
	::= { wirelessIfWORPTableEntry 8 }

wirelessIfWORPMultiFrameBursting  OBJECT-TYPE
	SYNTAX     INTEGER {
		enable (1),
		disable (2)
	}
	MAX-ACCESS read-write
	STATUS     current
	DESCRIPTION 
		"This parameter enables WORP protocol to allow each side, BSU or SU, to send
		                 a burst of multiple data messages instead of a single data message."
	DEFVAL  { enable }
	::= { wirelessIfWORPTableEntry 9 }

wirelessIfWORPRegistrationTimeout  OBJECT-TYPE
	SYNTAX     Unsigned32 (1..10)
	MAX-ACCESS read-write
	STATUS     current
	DESCRIPTION 
		"This parameter represents the registration procedure timeout period for WORP 
		                 interface."
	DEFVAL  { 5 }
	::= { wirelessIfWORPTableEntry 11 }

wirelessIfWORPRetries  OBJECT-TYPE
	SYNTAX     Unsigned32 (0..10)
	MAX-ACCESS read-write
	STATUS     current
	DESCRIPTION 
		"This parameter represents the number of times the same worp frame need to be
		                 re-Transmitted, if it is not acknowledged by the peer."
	DEFVAL  { 3 }
	::= { wirelessIfWORPTableEntry 12 }

wirelessIfWORPTxRate  OBJECT-TYPE
	SYNTAX     Unsigned32
	MAX-ACCESS read-write
	STATUS     deprecated
	DESCRIPTION 
		"This parameter represents the WORP interface transmission rate. Please check the
		         object wirelessIfWORPSupportedTxRate for supported rates.
		         This is now deprecated. Instead use linkProfileTxRate."
	::= { wirelessIfWORPTableEntry 13 }

wirelessIfWORPSupportedTxRate  OBJECT-TYPE
	SYNTAX     DisplayString
	MAX-ACCESS read-only
	STATUS     deprecated
	DESCRIPTION 
		"This parameter displays the supported transmission rate based on  
		        Channel Bandwdith, Guard Interval and Number of Spacial Streams configuration.
		        This is now deprecated. Instead use linkProfileSupportedTxRate."
	::= { wirelessIfWORPTableEntry 14 }

wirelessIfWORPInputBandwidthLimit  OBJECT-TYPE
	SYNTAX     Unsigned32 (64..307200)
	MAX-ACCESS read-write
	STATUS     current
	DESCRIPTION 
		"This parameters represents the Bandwidth limit on Input direction.
		                 Default limit & maximum limit are based on the license file."
	DEFVAL  { 307200 }
	::= { wirelessIfWORPTableEntry 15 }

wirelessIfWORPOutputBandwidthLimit  OBJECT-TYPE
	SYNTAX     Unsigned32 (64..307200)
	MAX-ACCESS read-write
	STATUS     current
	DESCRIPTION 
		"This parameter represents the Bandwidth limit on Output direction.
		                 Default limit & maximum limit are based on the license file."
	DEFVAL  { 307200 }
	::= { wirelessIfWORPTableEntry 16 }

wirelessIfWORPBandwidthLimitType  OBJECT-TYPE
	SYNTAX     INTEGER {
		policing (1),
		shaping (2)
	}
	MAX-ACCESS read-write
	STATUS     current
	DESCRIPTION 
		"This parameter represents the bandwidth limit type - shaping or policing."
	DEFVAL  { policing }
	::= { wirelessIfWORPTableEntry 17 }

wirelessIfWORPSecurityProfileIndex  OBJECT-TYPE
	SYNTAX     INTEGER {
		one (1),
		two (2),
		three (3),
		four (4),
		five (5),
		six (6),
		seven (7),
		eight (8)
	}
	MAX-ACCESS read-write
	STATUS     current
	DESCRIPTION 
		"This parameter allows to configure the Security profile for 
		                 the WORP interface based on the index of the profile name
		                                 and this is Valid only on BSU."
	::= { wirelessIfWORPTableEntry 18 }

wirelessIfWORPRadiusProfileIndex  OBJECT-TYPE
	SYNTAX     INTEGER {
		one (1),
		two (2),
		three (3),
		four (4),
		five (5),
		six (6),
		seven (7),
		eight (8)
	}
	MAX-ACCESS read-write
	STATUS     current
	DESCRIPTION 
		"This parameter allows to configure the Radius profile for 
		                 the WORP interface based on the index of the profile
		                                  name and this is Valid only on BSU.."
	::= { wirelessIfWORPTableEntry 19 }

wirelessIfWORPMACACLStatus  OBJECT-TYPE
	SYNTAX     INTEGER {
		enable (1),
		disable (2)
	}
	MAX-ACCESS read-write
	STATUS     current
	DESCRIPTION 
		"This parameter is used to enable or disable the MAC access control list.
		                 This configuration is Valid only on BSU."
	DEFVAL  { disable }
	::= { wirelessIfWORPTableEntry 20 }

wirelessIfWORPRadiusMACACLStatus  OBJECT-TYPE
	SYNTAX     INTEGER {
		enable (1),
		disable (2)
	}
	MAX-ACCESS read-write
	STATUS     current
	DESCRIPTION 
		"This parameter is used to enable or disable the MAC ACL for Radius Profiles.
		                 This configuration is Valid only on BSU."
	DEFVAL  { disable }
	::= { wirelessIfWORPTableEntry 21 }

wirelessIfWORPRadiusAccStatus  OBJECT-TYPE
	SYNTAX     INTEGER {
		enable (1),
		disable (2)
	}
	MAX-ACCESS not-accessible
	STATUS     current
	DESCRIPTION 
		"This parameter is used to enable or disable the Radius Accounting Stats capture.
		                 This configuration is Valid only on BSU and currently this is not accessible."
	::= { wirelessIfWORPTableEntry 22 }

wirelessIfWORPIntfMacAddress  OBJECT-TYPE
	SYNTAX     MacAddress
	MAX-ACCESS read-only
	STATUS     current
	DESCRIPTION 
		"This parameter represents the MAC address of the wireless interface card."
	::= { wirelessIfWORPTableEntry 23 }

wirelessIfWORPAutoMultiFrameBursting  OBJECT-TYPE
	SYNTAX     INTEGER {
		enable (1),
		disable (2)
	}
	MAX-ACCESS read-write
	STATUS     current
	DESCRIPTION 
		"This parameter enables WORP protocol to allow each side, BSU or SU, to send
		                                 a burst of multiple data messages based on QOS priority instead 
		                                 of a single data message."
	DEFVAL  { enable }
	::= { wirelessIfWORPTableEntry 24 }

wirelessIfWORPMaxTimedOutSatellites  OBJECT-TYPE
	SYNTAX     Integer32 (-1..0)
	MAX-ACCESS read-write
	STATUS     current
	DESCRIPTION 
		"This parameter represents the maximum timed out satellites
		                        -1 indicates disable
		                         0 indicates enable"
	DEFVAL  { -1 }
	::= { wirelessIfWORPTableEntry 25 }

wirelessIfWORPErrorCountThreshold  OBJECT-TYPE
	SYNTAX     Integer32 (0..100)
	MAX-ACCESS read-write
	STATUS     current
	DESCRIPTION 
		"This parameter represents WORP Error Count Threshold for sending TRAP."
	DEFVAL  { 0 }
	::= { wirelessIfWORPTableEntry 26 }

wirelessIfWORPRSSIDropThreshold  OBJECT-TYPE
	SYNTAX     Integer32 (0..50)
	MAX-ACCESS read-write
	STATUS     current
	DESCRIPTION 
		" This parameter represents WORP RSSI Level Drop Threshold for sending TRAP."
	DEFVAL  { 0 }
	::= { wirelessIfWORPTableEntry 27 }

wirelessIfWORPSecBaseStationName  OBJECT-TYPE
	SYNTAX     DisplayString (SIZE(0..32))
	MAX-ACCESS read-write
	STATUS     current
	DESCRIPTION 
		"This parameter represents the name of the Secondary/Redundant BSU for which it can 
		                 register. This configuration is valid only on SU."
	::= { wirelessIfWORPTableEntry 28 }

wirelessIfWORPBaseSwitchInterval  OBJECT-TYPE
	SYNTAX     Integer32 (2..60)
	MAX-ACCESS read-write
	STATUS     current
	DESCRIPTION 
		" This parameter represents the switching interval in minutes to Primary 
		                or Secondary BSU after worp link is established. This configuration 
		                is valid only on SU"
	DEFVAL  { 15 }
	::= { wirelessIfWORPTableEntry 29 }

wirelessIfWORPSyncStatus  OBJECT-TYPE
	SYNTAX     INTEGER {
		enable (1),
		disable (2)
	}
	MAX-ACCESS read-write
	STATUS     current
	DESCRIPTION 
		"This parameter is used to enable or disable the WORP Sync."
	DEFVAL  { disable }
	::= { wirelessIfWORPTableEntry 30 }

wirelessIfWORPSyncDLTimeFrame  OBJECT-TYPE
	SYNTAX     Unsigned32 (0..50000)
	MAX-ACCESS read-write
	STATUS     current
	DESCRIPTION 
		"This parameter is used to configure the WORP Sync downlink time frame.
		                 It is measured in microseconds."
	DEFVAL  { 0 }
	::= { wirelessIfWORPTableEntry 31 }

wirelessIfWORPSyncULTimeFrame  OBJECT-TYPE
	SYNTAX     Unsigned32 (0..50000)
	MAX-ACCESS read-write
	STATUS     current
	DESCRIPTION 
		"This parameter is used to configure the WORP Sync uplink time frame.
		                 It is measured in microseconds."
	DEFVAL  { 0 }
	::= { wirelessIfWORPTableEntry 32 }

wirelessIfWORPSyncInterFrameDelay  OBJECT-TYPE
	SYNTAX     Unsigned32 (0..50000)
	MAX-ACCESS read-write
	STATUS     current
	DESCRIPTION 
		"This parameter is used to configure the WORP Sync Interframe delay.
		                 It is measured in microseconds."
	DEFVAL  { 0 }
	::= { wirelessIfWORPTableEntry 33 }

wirelessIfWORPSyncIntraFrameDelay  OBJECT-TYPE
	SYNTAX     Unsigned32 (0..50000)
	MAX-ACCESS read-write
	STATUS     current
	DESCRIPTION 
		"This parameter is used to configure the WORP Sync IntraFrame delay.
		                 It is measured in microseconds."
	DEFVAL  { 0 }
	::= { wirelessIfWORPTableEntry 34 }

wirelessIfWORPSyncOffset  OBJECT-TYPE
	SYNTAX     Integer32 (-25000..25000)
	MAX-ACCESS read-write
	STATUS     current
	DESCRIPTION 
		"This parameter is used to configure the WORP Sync Time Base Offset.
		                 It is measured in microseconds."
	DEFVAL  { 0 }
	::= { wirelessIfWORPTableEntry 35 }

wirelessIfWORPSyncStopIfNoGPS  OBJECT-TYPE
	SYNTAX     INTEGER {
		no (1),
		yes (2)
	}
	MAX-ACCESS read-write
	STATUS     current
	DESCRIPTION 
		"This parameter is used to enable or disable the WORP Sync Source."
	DEFVAL  { no }
	::= { wirelessIfWORPTableEntry 36 }

wirelessIfWORPSyncDLSubSlots  OBJECT-TYPE
	SYNTAX     Unsigned32 (1..7)
	MAX-ACCESS read-write
	STATUS     current
	DESCRIPTION 
		"This parameter is used to configure the WORP Sync downlink time slots."
	DEFVAL  { 1 }
	::= { wirelessIfWORPTableEntry 37 }

wirelessIfWORPSyncULSubSlots  OBJECT-TYPE
	SYNTAX     Unsigned32 (1..7)
	MAX-ACCESS read-write
	STATUS     current
	DESCRIPTION 
		"This parameter is used to configure the WORP Sync uplink time slots."
	DEFVAL  { 1 }
	::= { wirelessIfWORPTableEntry 38 }

wirelessIfWORPSyncCompatibility  OBJECT-TYPE
	SYNTAX     INTEGER {
		proxim (1),
		cambium-pmp (2),
		custom (3),
		epmp (4)
	}
	MAX-ACCESS read-write
	STATUS     current
	DESCRIPTION 
		"This parameter is used to configure the WORP Sync pattern."
	DEFVAL  { proxim }
	::= { wirelessIfWORPTableEntry 39 }

wirelessIfWORPSyncDLRatio  OBJECT-TYPE
	SYNTAX     Unsigned32
	MAX-ACCESS read-write
	STATUS     current
	DESCRIPTION 
		"This parameter is used to configure the WORP Sync downlink/uplink ratio"
	DEFVAL  { 50 }
	::= { wirelessIfWORPTableEntry 40 }

wirelessIfWORPSyncMaxDistance  OBJECT-TYPE
	SYNTAX     Unsigned32 (0..40)
	MAX-ACCESS read-write
	STATUS     current
	DESCRIPTION 
		"This parameter is used to configure the WORP Sync maximum distance. Units- miles"
	DEFVAL  { 0 }
	::= { wirelessIfWORPTableEntry 41 }

wirelessIfWORPSyncControlSlots  OBJECT-TYPE
	SYNTAX     Unsigned32 (0..15)
	MAX-ACCESS read-write
	STATUS     current
	DESCRIPTION 
		"This Parameter is Used to configure the sync control slots"
	DEFVAL  { 0 }
	::= { wirelessIfWORPTableEntry 42 }

wirelessIfWORPSyncGPSSource  OBJECT-TYPE
	SYNTAX     INTEGER {
		ethernet (1),
		serial (2)
	}
	MAX-ACCESS read-write
	STATUS     current
	DESCRIPTION 
		"This Parameter is used to configure the Sync GPS Source."
	DEFVAL  { ethernet }
	::= { wirelessIfWORPTableEntry 43 }

wirelessIfWORPMinRSSIThrld  OBJECT-TYPE
	SYNTAX     Unsigned32 (0..100)
	MAX-ACCESS read-write
	STATUS     current
	DESCRIPTION 
		"This Parameter is Used to configure the minimum requried SNR for WORP link."
	DEFVAL  { 0 }
	::= { wirelessIfWORPTableEntry 44 }

wirelessIfWORPMinRSSIThrldOffset  OBJECT-TYPE
	SYNTAX     Unsigned32 (0..100)
	MAX-ACCESS read-write
	STATUS     current
	DESCRIPTION 
		"This Parameter is Used to configure the minimum requried SNR Offset."
	DEFVAL  { 0 }
	::= { wirelessIfWORPTableEntry 45 }

wirelessIfWORPLinkInactivityTimer  OBJECT-TYPE
	SYNTAX     Unsigned32 (0..3600)
	MAX-ACCESS read-write
	STATUS     current
	DESCRIPTION 
		"This parameter is used to configure WORP Link Inactivity timer in seconds."
	DEFVAL  { 0 }
	::= { wirelessIfWORPTableEntry 46 }

wirelessIfWORPDisconnectionInterval  OBJECT-TYPE
	SYNTAX     Unsigned32 (0|1000..10000)
	MAX-ACCESS read-write
	STATUS     current
	DESCRIPTION 
		"This parameter is used to configure the WORP Disconnection Interval value when
         minimum SNR is not proper. Units : milliSeconds"
	DEFVAL  { 0 }
	::= { wirelessIfWORPTableEntry 47 }

wirelessIfWORPTimeoutOffset  OBJECT-TYPE
	SYNTAX     Unsigned32 (0..100)
	MAX-ACCESS read-write
	STATUS     current
	DESCRIPTION 
		"This parameter is used to configure timeout offset. Units : milliSeconds"
	DEFVAL  { 3 }
	::= { wirelessIfWORPTableEntry 48 }

-- ======================================================================================
-- Definition of the WORP DDRS Group objects
-- ======================================================================================	
-- Worp DDRS Configuration Table

wirelessIfDDRSTable  OBJECT-TYPE
	SYNTAX SEQUENCE OF WirelessIfDDRSTableEntry
	MAX-ACCESS not-accessible
	STATUS     deprecated
	DESCRIPTION 
		"This table holds the WORP DDRS (Dynamic Data Rate Selection) feature
		                 configurations."
	::= { wirelessIf 5 }

wirelessIfDDRSTableEntry  OBJECT-TYPE
	SYNTAX 	WirelessIfDDRSTableEntry
	MAX-ACCESS not-accessible
	STATUS     deprecated
	DESCRIPTION 
		"This parameter represents the entry for DDRS table."
	INDEX { wirelessIfDDRSTableIndex }
	::= { wirelessIfDDRSTable 1 }

WirelessIfDDRSTableEntry ::= SEQUENCE {
	wirelessIfDDRSTableIndex
		Unsigned32,
	wirelessIfDDRSStatus
		INTEGER,
	wirelessIfDDRSDefDataRate
		Unsigned32,
	wirelessIfDDRSMaxDataRate
		Unsigned32,
	wirelessIfDDRSIncrAvgSNRThrld
		Unsigned32,
	wirelessIfDDRSIncrReqSNRThrld
		Unsigned32,
	wirelessIfDDRSDecrReqSNRThrld
		Unsigned32,
	wirelessIfDDRSIncrReTxPercentThrld
		Unsigned32,
	wirelessIfDDRSDecrReTxPercentThrld
		Unsigned32,
	wirelessIfDDRSAggressiveIndex
		Unsigned32,
	wirelessIfDDRSChainBalThrld
		Unsigned32,
	wirelessIfDDRSRateBackOffInt
		Unsigned32,
	wirelessIfDDRSRateBlackListInt
		Unsigned32,
	wirelessIfDDRSRateStableInt
		Unsigned32
}

wirelessIfDDRSTableIndex  OBJECT-TYPE
	SYNTAX     Unsigned32
	MAX-ACCESS read-only
	STATUS     deprecated
	DESCRIPTION 
		"This parameter represents the index for the DDRS table and indirectly represent the wireless interface index.
		                This is now deprecated."
	::= { wirelessIfDDRSTableEntry 1 }

wirelessIfDDRSStatus  OBJECT-TYPE
	SYNTAX     INTEGER {
		enable (1),
		disable (2)
	}
	MAX-ACCESS read-write
	STATUS     deprecated
	DESCRIPTION 
		"This parameter is used to enable/disable the DDRS feature for the interface.
		                This is now deprecated. Instead use linkProfileDDRSStatus."
	::= { wirelessIfDDRSTableEntry 2 }

wirelessIfDDRSDefDataRate  OBJECT-TYPE
	SYNTAX     Unsigned32
	MAX-ACCESS read-write
	STATUS     deprecated
	DESCRIPTION 
		"This default data rate shall be used as WORP default data rate only when the DDRS is enabled. The rates 
		                 defined in wirelessIfWORPTxRate are used as default. This is now deprecated.
		                 Instead use linkProfileDDRSMinDataRate."
	::= { wirelessIfDDRSTableEntry 3 }

wirelessIfDDRSMaxDataRate  OBJECT-TYPE
	SYNTAX     Unsigned32
	MAX-ACCESS read-write
	STATUS     deprecated
	DESCRIPTION 
		"This parameter is used to limit the maximum possible data rate that is set
		                 by DDRS. This is now deprecated. Instead use linkProfileDDRSMaxDataRate."
	::= { wirelessIfDDRSTableEntry 4 }

wirelessIfDDRSIncrAvgSNRThrld  OBJECT-TYPE
	SYNTAX     Unsigned32 (0..50)
	MAX-ACCESS read-write
	STATUS     deprecated
	DESCRIPTION 
		"This parameter is used to specify the average SNR threshold for data rate increase.
		                  The value should be in dB and in the range of 0..50 dB."
	::= { wirelessIfDDRSTableEntry 5 }

wirelessIfDDRSIncrReqSNRThrld  OBJECT-TYPE
	SYNTAX     Unsigned32 (0..50)
	MAX-ACCESS read-write
	STATUS     deprecated
	DESCRIPTION 
		"This parameter is to specify minimum required SNR threshold for data rate increase. 
		                The value should be in dB and in the range 0..50 dB. This is now deprecated.
		                Instead use linkProfileDDRSLowerSNRCorrection."
	::= { wirelessIfDDRSTableEntry 6 }

wirelessIfDDRSDecrReqSNRThrld  OBJECT-TYPE
	SYNTAX     Unsigned32 (0..50)
	MAX-ACCESS read-write
	STATUS     deprecated
	DESCRIPTION 
		"This parameter is to specify minimum required SNR threshold for data rate decrease. 
		                The value should be in dB and in the range 0..50 dB. This is now deprecated.
		                Instead use linkProfileDDRSUpperSNRCorrection."
	::= { wirelessIfDDRSTableEntry 7 }

wirelessIfDDRSIncrReTxPercentThrld  OBJECT-TYPE
	SYNTAX     Unsigned32 (1..100)
	MAX-ACCESS read-write
	STATUS     deprecated
	DESCRIPTION 
		"This object specifies the threshold percentage of retransmissions for 
		                DDRS data rate increase. This is now deprecated. Instead use linkProfileDDRSRateIncrRTXThrld."
	::= { wirelessIfDDRSTableEntry 8 }

wirelessIfDDRSDecrReTxPercentThrld  OBJECT-TYPE
	SYNTAX     Unsigned32 (1..100)
	MAX-ACCESS read-write
	STATUS     deprecated
	DESCRIPTION 
		"This object specifies the threshold percentage of retransmissions for 
		                DDRS data rate decrease. This is now deprecated. Instead use linkProfileDDRSRateDecrRTXThrld."
	::= { wirelessIfDDRSTableEntry 9 }

wirelessIfDDRSAggressiveIndex  OBJECT-TYPE
	SYNTAX     Unsigned32 (0..10)
	MAX-ACCESS read-write
	STATUS     deprecated
	DESCRIPTION 
		"This object specifies the aggressiveness of the ddrs algorithm. This is now deprecated."
	::= { wirelessIfDDRSTableEntry 10 }

wirelessIfDDRSChainBalThrld  OBJECT-TYPE
	SYNTAX     Unsigned32 (0..25)
	MAX-ACCESS read-write
	STATUS     deprecated
	DESCRIPTION 
		"This object specifies the Mimo Chain Balance threshold. This is now deprecated.
		                Instead use linkProfileDDRSChainBalThrld."
	::= { wirelessIfDDRSTableEntry 11 }

wirelessIfDDRSRateBackOffInt  OBJECT-TYPE
	SYNTAX     Unsigned32 (10..86400)
	MAX-ACCESS read-write
	STATUS     deprecated
	DESCRIPTION 
		"This object specifies the Rate Backoff Interval. This is now deprecated.
		                Instead use linkProfileDDRSRateBackOffInt."
	::= { wirelessIfDDRSTableEntry 12 }

wirelessIfDDRSRateBlackListInt  OBJECT-TYPE
	SYNTAX     Unsigned32 (10..86400)
	MAX-ACCESS read-write
	STATUS     deprecated
	DESCRIPTION 
		"This object specifies the Rate Blacklist Interval. This is now deprecated.
		                Instead use linkProfileDDRSRateBlacklistInt."
	::= { wirelessIfDDRSTableEntry 13 }

wirelessIfDDRSRateStableInt  OBJECT-TYPE
	SYNTAX     Unsigned32
	MAX-ACCESS read-write
	STATUS     deprecated
	DESCRIPTION 
		"This object specifies the Rate Stable Interval. This is now deprecated.
		                Instead use linkProfileDDRSRateStableInt."
	::= { wirelessIfDDRSTableEntry 14 }

-- Wireless Interface DDRS Minimum Required SNR Table

wirelessIfDDRSMinReqSNRTable  OBJECT-TYPE
	SYNTAX SEQUENCE OF WirelessIfDDRSMinReqSNRTableEntry
	MAX-ACCESS not-accessible
	STATUS     current
	DESCRIPTION 
		""
	::= { wirelessIf 6 }

wirelessIfDDRSMinReqSNRTableEntry  OBJECT-TYPE
	SYNTAX 	WirelessIfDDRSMinReqSNRTableEntry
	MAX-ACCESS not-accessible
	STATUS     current
	DESCRIPTION 
		""
	INDEX { wirelessIfDDRSMinReqSNRTableIndex, 
		wirelessIfDDRSMinReqSNRTableSecIndex }
	::= { wirelessIfDDRSMinReqSNRTable 1 }

WirelessIfDDRSMinReqSNRTableEntry ::= SEQUENCE {
	wirelessIfDDRSMinReqSNRTableIndex
		Unsigned32,
	wirelessIfDDRSMinReqSNRTableSecIndex
		Unsigned32,
	wirelessIfDDRSPhyModulation
		DisplayString,
	wirelessIfDDRSDataRate
		DisplayString,
	wirelessIfDDRSMinReqSNR
		Unsigned32,
	wirelessIfDDRSMCSIndex
		DisplayString,
	wirelessIfDDRSStreamMode
		DisplayString,
	wirelessIfDDRSMaxOptimalSNR
		Unsigned32
}

wirelessIfDDRSMinReqSNRTableIndex  OBJECT-TYPE
	SYNTAX     Unsigned32
	MAX-ACCESS read-only
	STATUS     current
	DESCRIPTION 
		""
	::= { wirelessIfDDRSMinReqSNRTableEntry 1 }

wirelessIfDDRSMinReqSNRTableSecIndex  OBJECT-TYPE
	SYNTAX     Unsigned32
	MAX-ACCESS read-only
	STATUS     current
	DESCRIPTION 
		""
	::= { wirelessIfDDRSMinReqSNRTableEntry 2 }

wirelessIfDDRSPhyModulation  OBJECT-TYPE
	SYNTAX     DisplayString
	MAX-ACCESS read-only
	STATUS     current
	DESCRIPTION 
		""
	::= { wirelessIfDDRSMinReqSNRTableEntry 3 }

wirelessIfDDRSDataRate  OBJECT-TYPE
	SYNTAX     DisplayString
	MAX-ACCESS read-only
	STATUS     current
	DESCRIPTION 
		""
	::= { wirelessIfDDRSMinReqSNRTableEntry 4 }

wirelessIfDDRSMinReqSNR  OBJECT-TYPE
	SYNTAX     Unsigned32 (1..100)
	MAX-ACCESS read-write
	STATUS     current
	DESCRIPTION 
		""
	::= { wirelessIfDDRSMinReqSNRTableEntry 5 }

wirelessIfDDRSMCSIndex  OBJECT-TYPE
	SYNTAX     DisplayString
	MAX-ACCESS read-only
	STATUS     current
	DESCRIPTION 
		""
	::= { wirelessIfDDRSMinReqSNRTableEntry 6 }

wirelessIfDDRSStreamMode  OBJECT-TYPE
	SYNTAX     DisplayString
	MAX-ACCESS read-only
	STATUS     current
	DESCRIPTION 
		""
	::= { wirelessIfDDRSMinReqSNRTableEntry 7 }

wirelessIfDDRSMaxOptimalSNR  OBJECT-TYPE
	SYNTAX     Unsigned32 (1..100)
	MAX-ACCESS read-write
	STATUS     current
	DESCRIPTION 
		""
	::= { wirelessIfDDRSMinReqSNRTableEntry 8 }

-- Wireless Interface Manual Blacklist Table

wirelessIfManualBlacklistTable  OBJECT-TYPE
	SYNTAX SEQUENCE OF WirelessIfManualBlacklistTableEntry
	MAX-ACCESS not-accessible
	STATUS     deprecated
	DESCRIPTION 
		""
	::= { wirelessIf 7 }

wirelessIfManualBlacklistTableEntry  OBJECT-TYPE
	SYNTAX 	WirelessIfManualBlacklistTableEntry
	MAX-ACCESS not-accessible
	STATUS     deprecated
	DESCRIPTION 
		""
	INDEX { wirelessIfManualBlacklistTableIndex, 
		wirelessIfManualBlacklistTableSecIndex }
	::= { wirelessIfManualBlacklistTable 1 }

WirelessIfManualBlacklistTableEntry ::= SEQUENCE {
	wirelessIfManualBlacklistTableIndex
		Unsigned32,
	wirelessIfManualBlacklistTableSecIndex
		Unsigned32,
	wirelessIfManualBlacklistChannel
		Unsigned32,
	wirelessIfManualBlacklistEntryStatus
		RowStatus
}

wirelessIfManualBlacklistTableIndex  OBJECT-TYPE
	SYNTAX     Unsigned32
	MAX-ACCESS read-only
	STATUS     deprecated
	DESCRIPTION 
		""
	::= { wirelessIfManualBlacklistTableEntry 1 }

wirelessIfManualBlacklistTableSecIndex  OBJECT-TYPE
	SYNTAX     Unsigned32
	MAX-ACCESS read-only
	STATUS     deprecated
	DESCRIPTION 
		""
	::= { wirelessIfManualBlacklistTableEntry 2 }

wirelessIfManualBlacklistChannel  OBJECT-TYPE
	SYNTAX     Unsigned32
	MAX-ACCESS read-write
	STATUS     deprecated
	DESCRIPTION 
		""
	::= { wirelessIfManualBlacklistTableEntry 3 }

wirelessIfManualBlacklistEntryStatus  OBJECT-TYPE
	SYNTAX     RowStatus
	MAX-ACCESS read-write
	STATUS     deprecated
	DESCRIPTION 
		""
	::= { wirelessIfManualBlacklistTableEntry 4 }

-- ======================================================================================
-- Definition of the Wireless If Roaming Group objects
-- ======================================================================================	
-- Wireless If Roaming

wirelessIfRoamingStatus  OBJECT-TYPE
	SYNTAX     INTEGER {
		enable (1),
		disable (2)
	}
	MAX-ACCESS read-write
	STATUS     current
	DESCRIPTION 
		"This parameter is used to enable or disable the roaming feature."
	DEFVAL  { disable }
	::= { wirelessIfRoamingTable 1 }

wirelessIfRoamingAnnouncePeriod  OBJECT-TYPE
	SYNTAX     Unsigned32 (25..100)
	MAX-ACCESS read-write
	STATUS     current
	DESCRIPTION 
		"This parameter is used to configure the roaming announce period.It is measured in milliseconds."
	DEFVAL  { 100 }
	::= { wirelessIfRoamingTable 2 }

wirelessIfRoamingMaximumPacketsPerBurst  OBJECT-TYPE
	SYNTAX     Unsigned32 (1..16)
	MAX-ACCESS read-write
	STATUS     current
	DESCRIPTION 
		"This parameter is used to configure the maximum packets that can be sent per burst."
	DEFVAL  { 16 }
	::= { wirelessIfRoamingTable 3 }

wirelessIfRoamingSlowRxRateThrld  OBJECT-TYPE
	SYNTAX     Unsigned32
	MAX-ACCESS read-write
	STATUS     deprecated
	DESCRIPTION 
		"This parameter is used to configure slow roaming sustainable Rx rate threshold."
	::= { wirelessIfRoamingTable 4 }

wirelessIfRoamingSlowTxRateThrld  OBJECT-TYPE
	SYNTAX     Unsigned32
	MAX-ACCESS read-write
	STATUS     deprecated
	DESCRIPTION 
		"This parameter is used to configure slow roaming sustainable Tx rate threshold."
	::= { wirelessIfRoamingTable 5 }

wirelessIfRoamingFastRxRateThrld  OBJECT-TYPE
	SYNTAX     Unsigned32
	MAX-ACCESS read-write
	STATUS     deprecated
	DESCRIPTION 
		"This parameter is used to configure the fast roaming sustainable Rx rate threshold."
	::= { wirelessIfRoamingTable 6 }

wirelessIfRoamingFastTxRateThrld  OBJECT-TYPE
	SYNTAX     Unsigned32
	MAX-ACCESS read-write
	STATUS     deprecated
	DESCRIPTION 
		"This parameter is used to configure the fast roaming sustainable Tx rate threshold."
	::= { wirelessIfRoamingTable 7 }

-- Wireless If Roaming Channel Table

wirelessIfRoamingChannelTable  OBJECT-TYPE
	SYNTAX SEQUENCE OF WirelessIfRoamingChannelEntry
	MAX-ACCESS not-accessible
	STATUS     current
	DESCRIPTION 
		""
	::= { wirelessIfRoamingTable 8 }

wirelessIfRoamingChannelEntry  OBJECT-TYPE
	SYNTAX 	WirelessIfRoamingChannelEntry
	MAX-ACCESS not-accessible
	STATUS     current
	DESCRIPTION 
		""
	INDEX { wirelessIfRoamingChannelTableIndex }
	::= { wirelessIfRoamingChannelTable 1 }

WirelessIfRoamingChannelEntry ::= SEQUENCE {
	wirelessIfRoamingChannelTableIndex
		Unsigned32,
	wirelessIfRoamingChannel
		Unsigned32,
	wirelessIfRoamingChannelEntryStatus
		RowStatus
}

wirelessIfRoamingChannelTableIndex  OBJECT-TYPE
	SYNTAX     Unsigned32
	MAX-ACCESS read-only
	STATUS     current
	DESCRIPTION 
		""
	::= { wirelessIfRoamingChannelEntry 1 }

wirelessIfRoamingChannel  OBJECT-TYPE
	SYNTAX     Unsigned32
	MAX-ACCESS read-write
	STATUS     current
	DESCRIPTION 
		"This parameter is used to configure the roaming channel number."
	::= { wirelessIfRoamingChannelEntry 2 }

wirelessIfRoamingChannelEntryStatus  OBJECT-TYPE
	SYNTAX     RowStatus
	MAX-ACCESS read-write
	STATUS     current
	DESCRIPTION 
		"This parameter is used to configure the wireless if roaming channel table status. 
		 It can be configured as
		                 active(enable) -1, 
		                 notInService(disable) - 2, 
		                 createAndGo(create row) -4, 
		                 destroy(delete) - 6"
	::= { wirelessIfRoamingChannelEntry 3 }

wirelessIfRoamingLinkProfileIndex  OBJECT-TYPE
	SYNTAX     Unsigned32
	MAX-ACCESS read-write
	STATUS     current
	DESCRIPTION 
		"This parameter is used to configure the index number of entry in the Link Profile Table."
	::= { wirelessIfRoamingTable 9 }

wirelessIfRoamingSlowRxSNRThrld  OBJECT-TYPE
	SYNTAX     Unsigned32 (0..127)
	MAX-ACCESS read-write
	STATUS     current
	DESCRIPTION 
		"This parameter is used to configure slow roaming sustainable Rx SNR threshold."
	::= { wirelessIfRoamingTable 10 }

wirelessIfRoamingFastRxSNRThrld  OBJECT-TYPE
	SYNTAX     Unsigned32 (0..127)
	MAX-ACCESS read-write
	STATUS     current
	DESCRIPTION 
		"This parameter is used to configure fast roaming sustainable Rx SNR threshold"
	::= { wirelessIfRoamingTable 11 }

wirelessIfRoamingToggleOffset  OBJECT-TYPE
	SYNTAX     Unsigned32 (0..10)
	MAX-ACCESS read-write
	STATUS     deprecated
	DESCRIPTION 
		"This parameter is used to during theselection of the best BSU to avoid ping pong effect."
	::= { wirelessIfRoamingTable 12 }

wirelessIfRoamingDownlinkBuffering  OBJECT-TYPE
	SYNTAX     Unsigned32
	MAX-ACCESS read-write
	STATUS     current
	DESCRIPTION 
		"This parameter is used to configure the roaming downlink buffering.
		         configure 1 - to enable downlink buffering
		                   0 - to disable downlink buffering"
	::= { wirelessIfRoamingTable 13 }

wirelessIfRoamingVLANId  OBJECT-TYPE
	SYNTAX     VlanId
	MAX-ACCESS read-write
	STATUS     current
	DESCRIPTION 
		"This Prameter is used to set the roaming Vlanid."
	DEFVAL  { -1 }
	::= { wirelessIfRoamingTable 14 }

wirelessIfRoamingNomadicMode  OBJECT-TYPE
	SYNTAX     INTEGER {
		enable (1),
		disable (2)
	}
	MAX-ACCESS read-write
	STATUS     current
	DESCRIPTION 
		"This parameter is used to enable or disable the nomadic mode."
	DEFVAL  { disable }
	::= { wirelessIfRoamingTable 15 }

wirelessIfRoamingTxRxDeltaSNR  OBJECT-TYPE
	SYNTAX     Unsigned32 (0..60)
	MAX-ACCESS read-write
	STATUS     current
	DESCRIPTION 
		"This parameter is used to configure delta SNR to trigger slow roaming."
	::= { wirelessIfRoamingTable 16 }

wirelessIfRoamingSNRToggleOffset  OBJECT-TYPE
	SYNTAX     Integer32 (-10..10)
	MAX-ACCESS read-write
	STATUS     current
	DESCRIPTION 
		"This parameter is used to during theselection of the best BSU to avoid ping pong effect."
	::= { wirelessIfRoamingTable 17 }

-- =============================================================================
-- The WORP Profile group: linkProfile
-- =============================================================================
-- Link Profile Table

linkProfileTable  OBJECT-TYPE
	SYNTAX SEQUENCE OF LinkProfileEntry
	MAX-ACCESS not-accessible
	STATUS     current
	DESCRIPTION 
		""
	::= { wirelessIf 9 }

linkProfileEntry  OBJECT-TYPE
	SYNTAX 	LinkProfileEntry
	MAX-ACCESS not-accessible
	STATUS     current
	DESCRIPTION 
		""
	INDEX { linkProfileTableIndex }
	::= { linkProfileTable 1 }

LinkProfileEntry ::= SEQUENCE {
	linkProfileTableIndex
		Unsigned32,
	linkProfileName
		DisplayString,
	linkProfileDDRSStatus
		INTEGER,
	linkProfileDDRSMinDataRate
		Unsigned32,
	linkProfileDDRSMaxDataRate
		Unsigned32,
	linkProfileDDRSLowerSNRCorrection
		Unsigned32,
	linkProfileDDRSUpperSNRCorrection
		Unsigned32,
	linkProfileDDRSRateIncrRTXThrld
		Unsigned32,
	linkProfileDDRSRateDecrRTXThrld
		Unsigned32,
	linkProfileDDRSChainBalThrld
		Unsigned32,
	linkProfileDDRSRateBackOffInt
		Unsigned32,
	linkProfileDDRSRateBlacklistInt
		Unsigned32,
	linkProfileDDRSRateStableInt
		Unsigned32,
	linkProfileATPCStatus
		INTEGER,
	linkProfileATPCUpperMargin
		Unsigned32,
	linkProfileATPCLowerMargin
		Unsigned32,
	linkProfileTPC
		Unsigned32,
	linkProfileTxRate
		Unsigned32,
	linkProfileSupportedTxRate
		DisplayString,
	linkProfileDataStreams
		INTEGER,
	linkProfileAutoTxAntStatus
		INTEGER,
	linkProfileTxAntChainMask
		INTEGER,
	linkProfileSupportedTxAntChainMask
		DisplayString,
	linkProfileTableEntryStatus
		RowStatus
}

linkProfileTableIndex  OBJECT-TYPE
	SYNTAX     Unsigned32
	MAX-ACCESS read-only
	STATUS     current
	DESCRIPTION 
		""
	::= { linkProfileEntry 1 }

linkProfileName  OBJECT-TYPE
	SYNTAX     DisplayString (SIZE(1..32))
	MAX-ACCESS read-write
	STATUS     current
	DESCRIPTION 
		"This parameter is used to configue the name of the profile."
	DEFVAL  { "default-profile" }
	::= { linkProfileEntry 2 }

linkProfileDDRSStatus  OBJECT-TYPE
	SYNTAX     INTEGER {
		enable (1),
		disable (2)
	}
	MAX-ACCESS read-write
	STATUS     current
	DESCRIPTION 
		"This parameter is used to enable or disable the DDRS feature for profile."
	DEFVAL  { enable }
	::= { linkProfileEntry 3 }

linkProfileDDRSMinDataRate  OBJECT-TYPE
	SYNTAX     Unsigned32
	MAX-ACCESS read-write
	STATUS     current
	DESCRIPTION 
		"This parameter is used to configure minimum data rate."
	::= { linkProfileEntry 4 }

linkProfileDDRSMaxDataRate  OBJECT-TYPE
	SYNTAX     Unsigned32
	MAX-ACCESS read-write
	STATUS     current
	DESCRIPTION 
		"This parameter is used to configure the maximum data rate."
	::= { linkProfileEntry 5 }

linkProfileDDRSLowerSNRCorrection  OBJECT-TYPE
	SYNTAX     Unsigned32 (0..50)
	MAX-ACCESS read-write
	STATUS     current
	DESCRIPTION 
		"This parameter is used to configure the minimum required SNR threshold for data rate 
		 increase. It is measured in dB."
	DEFVAL  { 0 }
	::= { linkProfileEntry 6 }

linkProfileDDRSUpperSNRCorrection  OBJECT-TYPE
	SYNTAX     Unsigned32 (0..50)
	MAX-ACCESS read-write
	STATUS     current
	DESCRIPTION 
		"This parameter is used to configure the minimum required SNR threshold for data rate 
		 decrease. It is measured in dB."
	DEFVAL  { 3 }
	::= { linkProfileEntry 7 }

linkProfileDDRSRateIncrRTXThrld  OBJECT-TYPE
	SYNTAX     Unsigned32 (1..100)
	MAX-ACCESS read-write
	STATUS     current
	DESCRIPTION 
		"This parameter is used to configure the retransmission threshold for rate increment in DDRS."
	DEFVAL  { 25 }
	::= { linkProfileEntry 8 }

linkProfileDDRSRateDecrRTXThrld  OBJECT-TYPE
	SYNTAX     Unsigned32 (1..100)
	MAX-ACCESS read-write
	STATUS     current
	DESCRIPTION 
		"This parameter is used to configure the retransmission threshold for rate decrement in DDRS."
	DEFVAL  { 30 }
	::= { linkProfileEntry 9 }

linkProfileDDRSChainBalThrld  OBJECT-TYPE
	SYNTAX     Unsigned32 (0..25)
	MAX-ACCESS read-write
	STATUS     current
	DESCRIPTION 
		"This parameter is used to configure the chain balance threshold for DDRS. It is measured in dB."
	DEFVAL  { 15 }
	::= { linkProfileEntry 10 }

linkProfileDDRSRateBackOffInt  OBJECT-TYPE
	SYNTAX     Unsigned32 (10..86400)
	MAX-ACCESS read-write
	STATUS     current
	DESCRIPTION 
		"This parameter is used to configure the rate backoff interval for DDRS."
	DEFVAL  { 300 }
	::= { linkProfileEntry 11 }

linkProfileDDRSRateBlacklistInt  OBJECT-TYPE
	SYNTAX     Unsigned32 (10..86400)
	MAX-ACCESS read-write
	STATUS     current
	DESCRIPTION 
		"This parameter is used to configure the rate blacklist interval for DDRS."
	DEFVAL  { 10 }
	::= { linkProfileEntry 12 }

linkProfileDDRSRateStableInt  OBJECT-TYPE
	SYNTAX     Unsigned32 (1..86400)
	MAX-ACCESS read-write
	STATUS     current
	DESCRIPTION 
		"This parameter is used to configure the rate stable interval for DDRS."
	DEFVAL  { 10 }
	::= { linkProfileEntry 13 }

linkProfileATPCStatus  OBJECT-TYPE
	SYNTAX     INTEGER {
		enable (1),
		disable (2)
	}
	MAX-ACCESS read-write
	STATUS     current
	DESCRIPTION 
		"This parameter is used to enable or disable the ATPC feature for profile."
	DEFVAL  { enable }
	::= { linkProfileEntry 14 }

linkProfileATPCUpperMargin  OBJECT-TYPE
	SYNTAX     Unsigned32 (0..20)
	MAX-ACCESS read-write
	STATUS     current
	DESCRIPTION 
		"This parameter is used to configure the lower margin for tpc decrement in ATPC. 
		 It is measured in dB."
	DEFVAL  { 10 }
	::= { linkProfileEntry 15 }

linkProfileATPCLowerMargin  OBJECT-TYPE
	SYNTAX     Unsigned32 (0..20)
	MAX-ACCESS read-write
	STATUS     current
	DESCRIPTION 
		"This parameter is used to configure the upper margin for tpc increment in ATPC. 
		 It is measured in dB."
	DEFVAL  { 0 }
	::= { linkProfileEntry 16 }

linkProfileTPC  OBJECT-TYPE
	SYNTAX     Unsigned32 (0..50)
	MAX-ACCESS read-write
	STATUS     current
	DESCRIPTION 
		"This parameter is used to configure the TPC to be applied for outgoing packets 
		 when ATPC is disabled. It is measured in dBm.
		 Configure the TPC value by multiplying with 2.
		 For example, to set TPC as 1.5, configure it as 3.
		 Obtained value divided by 2 gives the TPC."
	::= { linkProfileEntry 17 }

linkProfileTxRate  OBJECT-TYPE
	SYNTAX     Unsigned32
	MAX-ACCESS read-write
	STATUS     current
	DESCRIPTION 
		"This parameter is used to configure the Tx rate to be operated on when DDRS is disabled.
		 Please check the object linkProfileSupportedTxRate for supported rates."
	::= { linkProfileEntry 18 }

linkProfileSupportedTxRate  OBJECT-TYPE
	SYNTAX     DisplayString
	MAX-ACCESS read-only
	STATUS     current
	DESCRIPTION 
		"This parameter displays the supported transmission rate based on  
		 Channel Bandwdith, Guard Interval and Number of Spacial Streams 
		 configuration."
	::= { linkProfileEntry 19 }

linkProfileDataStreams  OBJECT-TYPE
	SYNTAX     INTEGER {
		single (1),
		dual (2),
		auto (3)
	}
	MAX-ACCESS read-write
	STATUS     current
	DESCRIPTION 
		"This parameter is used to configure stream mode.
		 Default is value is auto if DDRS is enabled,
		 dual if DDRS is disabled."
	::= { linkProfileEntry 20 }

linkProfileAutoTxAntStatus  OBJECT-TYPE
	SYNTAX     INTEGER {
		enable (1),
		disable (2)
	}
	MAX-ACCESS read-write
	STATUS     current
	DESCRIPTION 
		"This parameter is used to enable or disable the auto tx antenna feature. 
		 This is enbaled by default when single stream mode is set."
	DEFVAL  { disable }
	::= { linkProfileEntry 21 }

linkProfileTxAntChainMask  OBJECT-TYPE
	SYNTAX     INTEGER {
		one (1),
		two (2),
		three (3),
		four (4),
		five (5),
		six (6),
		seven (7)
	}
	MAX-ACCESS read-write
	STATUS     current
	DESCRIPTION 
		"This parameter is used to configure the Tx Antenna chain mask. This is configured as bitmask.
		 Please check the object linkProfileSupportedTxAntChainMask for supported chain mask.
		         Eg: 3 - 011 (binary value) - first and second antennas are enabled. 
		             7 - 111 (binary value) - all three are enabled."
	DEFVAL  { seven }
	::= { linkProfileEntry 22 }

linkProfileSupportedTxAntChainMask  OBJECT-TYPE
	SYNTAX     DisplayString (SIZE(1..64))
	MAX-ACCESS read-only
	STATUS     current
	DESCRIPTION 
		"This parameter shows the number of supported Tx antennas."
	::= { linkProfileEntry 23 }

linkProfileTableEntryStatus  OBJECT-TYPE
	SYNTAX     RowStatus
	MAX-ACCESS read-write
	STATUS     current
	DESCRIPTION 
		"This parameter is used to configure the row status for the ProfileTable. 
		                    It can be configured as 
		                    active(enable) -1, 
		                    notInService(disable) - 2, 
		                    createAndGo(create row) -4, 
		                    destroy(delete) - 6"
	::= { linkProfileEntry 24 }

-- ======================================================================================
-- Definition of the WORP Profile Peer Group objects
-- ======================================================================================	
-- WORP Profile Peer Table

wirelessIfWORPProfilePeerTable  OBJECT-TYPE
	SYNTAX SEQUENCE OF WirelessIfWORPProfilePeerEntry
	MAX-ACCESS not-accessible
	STATUS     current
	DESCRIPTION 
		""
	::= { wirelessIf 10 }

wirelessIfWORPProfilePeerEntry  OBJECT-TYPE
	SYNTAX 	WirelessIfWORPProfilePeerEntry
	MAX-ACCESS not-accessible
	STATUS     current
	DESCRIPTION 
		""
	INDEX { wirelessIfWORPProfilePeerTableIndex }
	::= { wirelessIfWORPProfilePeerTable 1 }

WirelessIfWORPProfilePeerEntry ::= SEQUENCE {
	wirelessIfWORPProfilePeerTableIndex
		Unsigned32,
	wirelessIfWORPProfilePeerMACAddress
		MacAddress,
	wirelessIfWORPProfilePeerDeviceName
		DisplayString,
	wirelessIfWORPProfilePeerProfileIndex
		Unsigned32,
	wirelessIfWORPProfilePeerTableEntryStatus
		RowStatus
}

wirelessIfWORPProfilePeerTableIndex  OBJECT-TYPE
	SYNTAX     Unsigned32
	MAX-ACCESS read-only
	STATUS     current
	DESCRIPTION 
		""
	::= { wirelessIfWORPProfilePeerEntry 1 }

wirelessIfWORPProfilePeerMACAddress  OBJECT-TYPE
	SYNTAX     MacAddress
	MAX-ACCESS read-write
	STATUS     current
	DESCRIPTION 
		"This parameter is used to configure the wireless MAC address of the peer."
	::= { wirelessIfWORPProfilePeerEntry 2 }

wirelessIfWORPProfilePeerDeviceName  OBJECT-TYPE
	SYNTAX     DisplayString (SIZE(0..32))
	MAX-ACCESS read-write
	STATUS     current
	DESCRIPTION 
		"This parameter is used to configure the name of the peer."
	::= { wirelessIfWORPProfilePeerEntry 3 }

wirelessIfWORPProfilePeerProfileIndex  OBJECT-TYPE
	SYNTAX     Unsigned32
	MAX-ACCESS read-write
	STATUS     current
	DESCRIPTION 
		"This parameter is used to configure the index number of entry in the Profile Table."
	::= { wirelessIfWORPProfilePeerEntry 4 }

wirelessIfWORPProfilePeerTableEntryStatus  OBJECT-TYPE
	SYNTAX     RowStatus
	MAX-ACCESS read-write
	STATUS     current
	DESCRIPTION 
		"This parameter is used to configure the row status for the wirelessIfWORPProfilePeerTable. 
		                    It can be configured as 
		                    active(enable) -1, 
		                    notInService(disable) - 2, 
		                    createAndGo(create row) -4, 
		                    destroy(delete) - 6"
	::= { wirelessIfWORPProfilePeerEntry 5 }

-- ======================================================================================
-- Definition of the wirelessIfScanAcrossBandWidthTable  Group objects
-- ======================================================================================	
-- wirelessIf ScanAcrossBandWidth Table

wirelessIfScanAcrossBandWidthStatus  OBJECT-TYPE
	SYNTAX     INTEGER {
		enable (1),
		disable (2)
	}
	MAX-ACCESS read-write
	STATUS     current
	DESCRIPTION 
		""
	DEFVAL  { disable }
	::= { wirelessIfScanAcrossBandWidthTable 1 }

wirelessIfBandWidthTable  OBJECT-TYPE
	SYNTAX SEQUENCE OF WirelessIfBandWidthEntry
	MAX-ACCESS not-accessible
	STATUS     current
	DESCRIPTION 
		""
	::= { wirelessIfScanAcrossBandWidthTable 2 }

wirelessIfBandWidthEntry  OBJECT-TYPE
	SYNTAX 	WirelessIfBandWidthEntry
	MAX-ACCESS not-accessible
	STATUS     current
	DESCRIPTION 
		""
	INDEX { wirelessIfBandWidthIndex }
	::= { wirelessIfBandWidthTable 1 }

WirelessIfBandWidthEntry ::= SEQUENCE {
	wirelessIfBandWidthIndex
		Unsigned32,
	wirelessIfAvailableBandwidth
		Unsigned32,
	wirelessIfBandWidthEntryStatus
		RowStatus
}

wirelessIfBandWidthIndex  OBJECT-TYPE
	SYNTAX     Unsigned32
	MAX-ACCESS read-only
	STATUS     current
	DESCRIPTION 
		""
	::= { wirelessIfBandWidthEntry 1 }

wirelessIfAvailableBandwidth  OBJECT-TYPE
	SYNTAX     Unsigned32
	MAX-ACCESS read-write
	STATUS     current
	DESCRIPTION 
		""
	::= { wirelessIfBandWidthEntry 2 }

wirelessIfBandWidthEntryStatus  OBJECT-TYPE
	SYNTAX     RowStatus
	MAX-ACCESS read-write
	STATUS     current
	DESCRIPTION 
		""
	::= { wirelessIfBandWidthEntry 3 }

-- ======================================================================================
-- Definition of the wirelessIfScanAcrossOffsetTable  Group objects
-- ======================================================================================	
-- wirelessIf ScanAcrossOffset Table

wirelessIfScanAcrossOffsetStatus  OBJECT-TYPE
	SYNTAX     INTEGER {
		enable (1),
		disable (2)
	}
	MAX-ACCESS read-write
	STATUS     current
	DESCRIPTION 
		""
	DEFVAL  { disable }
	::= { wirelessIfScanAcrossOffsetTable 1 }

wirelessIfOffsetTable  OBJECT-TYPE
	SYNTAX SEQUENCE OF WirelessIfOffsetEntry
	MAX-ACCESS not-accessible
	STATUS     current
	DESCRIPTION 
		""
	::= { wirelessIfScanAcrossOffsetTable 2 }

wirelessIfOffsetEntry  OBJECT-TYPE
	SYNTAX 	WirelessIfOffsetEntry
	MAX-ACCESS not-accessible
	STATUS     current
	DESCRIPTION 
		""
	INDEX { wirelessIfOffsetIndex }
	::= { wirelessIfOffsetTable 1 }

WirelessIfOffsetEntry ::= SEQUENCE {
	wirelessIfOffsetIndex
		Unsigned32,
	wirelessIfAvailableOffset
		Integer32,
	wirelessIfOffsetEntryStatus
		RowStatus
}

wirelessIfOffsetIndex  OBJECT-TYPE
	SYNTAX     Unsigned32
	MAX-ACCESS read-only
	STATUS     current
	DESCRIPTION 
		""
	::= { wirelessIfOffsetEntry 1 }

wirelessIfAvailableOffset  OBJECT-TYPE
	SYNTAX     Integer32 (-2..2)
	MAX-ACCESS read-write
	STATUS     current
	DESCRIPTION 
		""
	::= { wirelessIfOffsetEntry 2 }

wirelessIfOffsetEntryStatus  OBJECT-TYPE
	SYNTAX     RowStatus
	MAX-ACCESS read-write
	STATUS     current
	DESCRIPTION 
		""
	::= { wirelessIfOffsetEntry 3 }

-- ======================================================================================
-- Definition of the wirelessIfMFBTable  Group objects
-- ======================================================================================	
-- wirelessIfMFB Table

wirelessIfMFBTable  OBJECT-TYPE
	SYNTAX SEQUENCE OF WirelessIfMFBTableEntry
	MAX-ACCESS not-accessible
	STATUS     current
	DESCRIPTION 
		""
	::= { wirelessIf 13 }

wirelessIfMFBTableEntry  OBJECT-TYPE
	SYNTAX 	WirelessIfMFBTableEntry
	MAX-ACCESS not-accessible
	STATUS     current
	DESCRIPTION 
		""
	INDEX { wirelessIfMFBTableIndex, 
		wirelessIfMFBTableSecIndex }
	::= { wirelessIfMFBTable 1 }

WirelessIfMFBTableEntry ::= SEQUENCE {
	wirelessIfMFBTableIndex
		Integer32,
	wirelessIfMFBTableSecIndex
		Unsigned32,
	wirelessIfMFBStartFrequency
		Unsigned32,
	wirelessIfMFBEndFrequency
		Unsigned32,
	wirelessIfMFBEntryStatus
		RowStatus
}

wirelessIfMFBTableIndex  OBJECT-TYPE
	SYNTAX     Integer32 (1..256)
	MAX-ACCESS read-only
	STATUS     current
	DESCRIPTION 
		""
	::= { wirelessIfMFBTableEntry 1 }

wirelessIfMFBTableSecIndex  OBJECT-TYPE
	SYNTAX     Unsigned32
	MAX-ACCESS read-only
	STATUS     current
	DESCRIPTION 
		""
	::= { wirelessIfMFBTableEntry 2 }

wirelessIfMFBStartFrequency  OBJECT-TYPE
	SYNTAX     Unsigned32 (0..10000)
	MAX-ACCESS read-write
	STATUS     current
	DESCRIPTION 
		""
	::= { wirelessIfMFBTableEntry 3 }

wirelessIfMFBEndFrequency  OBJECT-TYPE
	SYNTAX     Unsigned32 (0..10000)
	MAX-ACCESS read-write
	STATUS     current
	DESCRIPTION 
		""
	::= { wirelessIfMFBTableEntry 4 }

wirelessIfMFBEntryStatus  OBJECT-TYPE
	SYNTAX     RowStatus
	MAX-ACCESS read-write
	STATUS     current
	DESCRIPTION 
		""
	::= { wirelessIfMFBTableEntry 5 }

-- ======================================================================================
-- Definition of the wirelessIfWhiteChanTable  Group objects
-- ======================================================================================	

-- wirelessIfWhiteChanTable

wirelessIfWhiteChanTable  OBJECT-TYPE
	SYNTAX SEQUENCE OF WirelessIfWhiteChanEntry
	MAX-ACCESS not-accessible
	STATUS     current
	DESCRIPTION 
		"White Channel table. "
	::= { wirelessIf 14 }

wirelessIfWhiteChanEntry  OBJECT-TYPE
	SYNTAX 	WirelessIfWhiteChanEntry
	MAX-ACCESS not-accessible
	STATUS     current
	DESCRIPTION 
		"This parameter is used to define the entry status."
	INDEX { wirelessIfWhiteChanTableIndex, 
		wirelessIfWhiteChanTableSecIndex }
	::= { wirelessIfWhiteChanTable 1 }

WirelessIfWhiteChanEntry ::= SEQUENCE {
	wirelessIfWhiteChanTableIndex
		Unsigned32,
	wirelessIfWhiteChanTableSecIndex
		Unsigned32,
	wirelessIfWhiteChannel
		Unsigned32,
	wirelessIfWhiteFrequency
		Unsigned32,
	wirelessIfWhiteChanEntryStatus
		RowStatus
}

wirelessIfWhiteChanTableIndex  OBJECT-TYPE
	SYNTAX     Unsigned32
	MAX-ACCESS read-only
	STATUS     current
	DESCRIPTION 
		"This parameter is used for White Channel table radio index."
	::= { wirelessIfWhiteChanEntry 1 }

wirelessIfWhiteChanTableSecIndex  OBJECT-TYPE
	SYNTAX     Unsigned32 (1..256)
	MAX-ACCESS read-only
	STATUS     current
	DESCRIPTION 
		"This parameter is used for White Channel table sec index."
	::= { wirelessIfWhiteChanEntry 2 }

wirelessIfWhiteChannel  OBJECT-TYPE
	SYNTAX     Unsigned32
	MAX-ACCESS read-write
	STATUS     current
	DESCRIPTION 
		"This parameter is used for White Channel."
	::= { wirelessIfWhiteChanEntry 3 }

wirelessIfWhiteFrequency  OBJECT-TYPE
	SYNTAX     Unsigned32
	MAX-ACCESS read-write
	STATUS     current
	DESCRIPTION 
		"This parameter is used for White Channel."
	::= { wirelessIfWhiteChanEntry 4 }

wirelessIfWhiteChanEntryStatus  OBJECT-TYPE
	SYNTAX     RowStatus
	MAX-ACCESS read-write
	STATUS     current
	DESCRIPTION 
		"This parameter is used for White Channel entry status."
	::= { wirelessIfWhiteChanEntry 5 }


-- =====================================================================================
-- Ethernet Interface Subgroup : EthernetIf
-- =====================================================================================
-- Ethernet Interface Properties Table 

ethernetIfPropertiesTable  OBJECT-TYPE
	SYNTAX SEQUENCE OF EthernetIfPropertiesTableEntry
	MAX-ACCESS not-accessible
	STATUS     current
	DESCRIPTION 
		"This table shows the ethernet interface(s) properties for the device."
	::= { ethernetIf 1 }

ethernetIfPropertiesTableEntry  OBJECT-TYPE
	SYNTAX 	EthernetIfPropertiesTableEntry
	MAX-ACCESS not-accessible
	STATUS     current
	DESCRIPTION 
		"This parameter represents the entry for the Ethernet Interface Properties table."
	INDEX { ethernetIfPropertiesTableIndex }
	::= { ethernetIfPropertiesTable 1 }

EthernetIfPropertiesTableEntry ::= SEQUENCE {
	ethernetIfPropertiesTableIndex
		Unsigned32,
	ethernetIfMACAddress
		MacAddress,
	ethernetIfSupportedSpeed
		INTEGER,
	ethernetIfSupportedTxMode
		INTEGER,
	ethernetIfTxModeAndSpeed
		INTEGER,
	ethernetIfSupportedModes
		DisplayString,
	ethernetIfAdminStatus
		INTEGER,
	ethernetIfAutoShutDown
		INTEGER
}

ethernetIfPropertiesTableIndex  OBJECT-TYPE
	SYNTAX     Unsigned32 (1)
	MAX-ACCESS read-only
	STATUS     current
	DESCRIPTION 
		"This parameter represents the physical interface and used as index to this table."
	::= { ethernetIfPropertiesTableEntry 1 }

ethernetIfMACAddress  OBJECT-TYPE
	SYNTAX     MacAddress
	MAX-ACCESS read-only
	STATUS     current
	DESCRIPTION 
		"This parameter represents the MAC address for the ethernet interface."
	::= { ethernetIfPropertiesTableEntry 2 }

ethernetIfSupportedSpeed  OBJECT-TYPE
	SYNTAX     INTEGER {
		auto (1),
		oneGbps (2),
		tenMbps (3),
		hundredMbit (4),
		unknown (5)
	}
	MAX-ACCESS read-only
	STATUS     current
	DESCRIPTION 
		"This parameter shows the supported speeds for the ethernet interface."
	::= { ethernetIfPropertiesTableEntry 3 }

ethernetIfSupportedTxMode  OBJECT-TYPE
	SYNTAX     INTEGER {
		halfDuplex (1),
		fullDuplex (2),
		auto (3),
		unknown (4)
	}
	MAX-ACCESS read-only
	STATUS     current
	DESCRIPTION 
		"This parameter shows the supported transmit modes of the ethernet 
		 interface."
	::= { ethernetIfPropertiesTableEntry 4 }

ethernetIfTxModeAndSpeed  OBJECT-TYPE
	SYNTAX     INTEGER {
		auto (1),
		tenMbps-halfDuplex (2),
		tenMbps-fullDuplex (3),
		hundredMbps-halfDuplex (4),
		hundredMbps-fullDuplex (5),
		oneGbps-fullDuplex (6)
	}
	MAX-ACCESS read-write
	STATUS     current
	DESCRIPTION 
		"This parameter is used to configure the Transmit Mode and speed of the 
		                 ethernet interface."
	::= { ethernetIfPropertiesTableEntry 5 }

ethernetIfSupportedModes  OBJECT-TYPE
	SYNTAX     DisplayString
	MAX-ACCESS read-only
	STATUS     current
	DESCRIPTION 
		"This parameter is used to display the supported modes on ethernet interface."
	::= { ethernetIfPropertiesTableEntry 6 }

ethernetIfAdminStatus  OBJECT-TYPE
	SYNTAX     INTEGER {
		enable (1),
		disable (2)
	}
	MAX-ACCESS read-write
	STATUS     current
	DESCRIPTION 
		"This parameter is used to configure the admin status for the ethernet interface."
	::= { ethernetIfPropertiesTableEntry 7 }

ethernetIfAutoShutDown  OBJECT-TYPE
	SYNTAX     INTEGER {
		enable (1),
		disable (2)
	}
	MAX-ACCESS read-write
	STATUS     current
	DESCRIPTION 
		"This parameter is used to configure AutoShutDown for the ethernet interface.
		i.e. Ethernet interface will be automatically UP/DOWN depending upon the wireless link "
	::= { ethernetIfPropertiesTableEntry 8 }

-- ======================================================================================
-- Security Group Objects
-- ======================================================================================
-- ======================================================================================
-- Wireless Security Subgroup Objects : wirelessSecurity
-- ======================================================================================
-- Wireless Security Configuration Table 

wirelessSecurityCfgTable  OBJECT-TYPE
	SYNTAX SEQUENCE OF WirelessSecurityCfgTableEntry
	MAX-ACCESS not-accessible
	STATUS     current
	DESCRIPTION 
		"This table is used to specify the security configuration for 
		              the wireless interface(s) in the access point."
	::= { wirelessSecurity 1 }

wirelessSecurityCfgTableEntry  OBJECT-TYPE
	SYNTAX 	WirelessSecurityCfgTableEntry
	MAX-ACCESS not-accessible
	STATUS     current
	DESCRIPTION 
		"This parameter represents an entry in the wireless security configuration table.
		 This table supports up to 8 entries."
	INDEX { wirelessSecurityCfgTableIndex }
	::= { wirelessSecurityCfgTable 1 }

WirelessSecurityCfgTableEntry ::= SEQUENCE {
	wirelessSecurityCfgTableIndex
		Unsigned32,
	wirelessSecurityCfgprofileName
		DisplayString,
	wirelessSecurityCfgAuthenticationMode
		INTEGER,
	wirelessSecurityCfgKeyIndex
		INTEGER,
	wirelessSecurityCfgKey1
		WEPKeyType,
	wirelessSecurityCfgdot1xWepKeyLength
		INTEGER,
	wirelessSecurityCfgEncryptionType
		INTEGER,
	wirelessSecurityCfgPSK
		DisplayString,
	wirelessSecurityCfgRekeyingInterval
		Unsigned32,
	wirelessSecurityCfgEntryStatus
		RowStatus,
	wirelessSecurityCfgNetworkSecret
		DisplayString,
	wirelessSecurityCfgKey2
		WEPKeyType,
	wirelessSecurityCfgKey3
		WEPKeyType,
	wirelessSecurityCfgKey4
		WEPKeyType,
	wirelessSecurityProfileGroupType
		INTEGER
}

wirelessSecurityCfgTableIndex  OBJECT-TYPE
	SYNTAX     Unsigned32 (1..16)
	MAX-ACCESS read-only
	STATUS     current
	DESCRIPTION 
		"This parameter is used as index to the wireless security configuration table."
	::= { wirelessSecurityCfgTableEntry 1 }

wirelessSecurityCfgprofileName  OBJECT-TYPE
	SYNTAX     DisplayString (SIZE(1..32))
	MAX-ACCESS read-write
	STATUS     current
	DESCRIPTION 
		"This paramater represents user defined profile name for security configuration."
	DEFVAL  { "DEFAULT SECURITY" }
	::= { wirelessSecurityCfgTableEntry 2 }

wirelessSecurityCfgAuthenticationMode  OBJECT-TYPE
	SYNTAX     INTEGER {
		none (1),
		wep (2),
		psk (3),
		dot1x (4),
		worp (5)
	}
	MAX-ACCESS read-create
	STATUS     current
	DESCRIPTION 
		"This parameter is used to configure the security authentication 
		 mode for wireless. Select 
		 (1) - None (no security), 
		 (2) - WEP (Wired Equivalent Privacy),  
		 (3) - PSK (Pre-shared key),   
		 (4) - dotlx (802.1x authentication) and
		                 (5) - worp (Wireless Outdoor Router Protocol)."
	DEFVAL  { none }
	::= { wirelessSecurityCfgTableEntry 3 }

wirelessSecurityCfgKeyIndex  OBJECT-TYPE
	SYNTAX     INTEGER {
		one (1),
		two (2),
		three (3),
		four (4)
	}
	MAX-ACCESS read-write
	STATUS     current
	DESCRIPTION 
		"This parameter represents the encryption key index that is 
		 used to encrypt data that is sent via wireless interface(s)."
	::= { wirelessSecurityCfgTableEntry 4 }

wirelessSecurityCfgKey1  OBJECT-TYPE
	SYNTAX     WEPKeyType
	MAX-ACCESS read-write
	STATUS     current
	DESCRIPTION 
		"This parameter represents the key 1 used for wireless security 
		 configuration. The key lengths 5/13/16 in ASCII or 10/26/32
		                 in HEXADECIMAL configures the WEP(64/128/152-bit) encryption respectively. 
		                 The key lengths 16 in ASCII or 32 in HEXADECIMAL configures the 
		                 TKIP(128-bit) or AES-CCM(128-bit) encryption."
	::= { wirelessSecurityCfgTableEntry 5 }

wirelessSecurityCfgdot1xWepKeyLength  OBJECT-TYPE
	SYNTAX     INTEGER {
		wep64 (1),
		wep128 (2)
	}
	MAX-ACCESS read-write
	STATUS     current
	DESCRIPTION 
		"This parameter is used configure the length of the security key. Select 
		 WEP64 if you want to have a security key for 64 characters or 
		 WEP128 for security key length of 128 characters."
	DEFVAL  { wep64 }
	::= { wirelessSecurityCfgTableEntry 6 }

wirelessSecurityCfgEncryptionType  OBJECT-TYPE
	SYNTAX     INTEGER {
		none (0),
		wep (1),
		wpa-tkip (2),
		wpa2-aes (3),
		wpa-wpa2aes-tkip (4),
		wpa2-aes-ccm (5),
		tkip (6),
		aes-ccm (7)
	}
	MAX-ACCESS read-write
	STATUS     current
	DESCRIPTION 
		"This parameter is used to configure the encryption key type for
		 wireless security. Select
		                 0 for no security 
		 1 for WEP, 
		 2 for WPA (TKIP), 
		 3 for WPA2(AES), 
		 4 for WPA/WPA2 (AES-TKIP)
		 5 for WPA2 (AES-CCM).
		                 6 for TKIP -- Used only for TMP/QB products
		                 7 for AES-CCM -- Used only for TMP/QB products."
	DEFVAL  { wep }
	::= { wirelessSecurityCfgTableEntry 7 }

wirelessSecurityCfgPSK  OBJECT-TYPE
	SYNTAX     DisplayString (SIZE(1..32))
	MAX-ACCESS read-write
	STATUS     current
	DESCRIPTION 
		"This parameter is used to configure the pre-share key. The default 
		 key is 123456789. This parameter is logically write-only. Reading 
		 this variable shall return astericks"
	DEFVAL  { "123456789" }
	::= { wirelessSecurityCfgTableEntry 8 }

wirelessSecurityCfgRekeyingInterval  OBJECT-TYPE
	SYNTAX     Unsigned32 (900..65535)
	MAX-ACCESS read-write
	STATUS     current
	DESCRIPTION 
		"This parameter represents the key re-negotiation time in case of dynamic
		  WEP, WPA/WPA-2 (personal/enterprise) security mechanisms."
	DEFVAL  { 900 }
	::= { wirelessSecurityCfgTableEntry 9 }

wirelessSecurityCfgEntryStatus  OBJECT-TYPE
	SYNTAX     RowStatus
	MAX-ACCESS read-write
	STATUS     current
	DESCRIPTION 
		"This parameter is used to configure the entry status of wireless
		 security configuration table.
		 It can be configured as 
		                 active(enable) -1, 
		                 notInService(disable) - 2, 
		                 createAndGo(create row) -4, 
		                 destroy(delete) - 6"
	DEFVAL  { active }
	::= { wirelessSecurityCfgTableEntry 10 }

wirelessSecurityCfgNetworkSecret  OBJECT-TYPE
	SYNTAX     DisplayString (SIZE(6..32))
	MAX-ACCESS read-write
	STATUS     current
	DESCRIPTION 
		"This parameter represents a secret password of an SU that tallies
		                 with the BSU's  password for authentic registration."
	DEFVAL  { "public" }
	::= { wirelessSecurityCfgTableEntry 11 }

wirelessSecurityCfgKey2  OBJECT-TYPE
	SYNTAX     WEPKeyType
	MAX-ACCESS read-write
	STATUS     current
	DESCRIPTION 
		"This parameter represents the key 2 used for wireless security 
		                 configuration. The key lengths 5/13/16 in ASCII or 10/26/32
		                 in HEXADECIMAL configures the WEP(64/128/152-bit) encryption respectively. 
		                 The key lengths 16 in ASCII or 32 in HEXADECIMAL configures the 
		                 TKIP(128-bit) or AES-CCM(128-bit) encryption."
	::= { wirelessSecurityCfgTableEntry 12 }

wirelessSecurityCfgKey3  OBJECT-TYPE
	SYNTAX     WEPKeyType
	MAX-ACCESS read-write
	STATUS     current
	DESCRIPTION 
		"This parameter represents the key 3 used for wireless security 
		                 configuration. The key lengths 5/13/16 in ASCII or 10/26/32
		                 in HEXADECIMAL configures the WEP(64/128/152-bit) encryption respectively. 
		                 The key lengths 16 in ASCII or 32 in HEXADECIMAL configures the 
		                 TKIP(128-bit) or AES-CCM(128-bit) encryption."
	::= { wirelessSecurityCfgTableEntry 13 }

wirelessSecurityCfgKey4  OBJECT-TYPE
	SYNTAX     WEPKeyType
	MAX-ACCESS read-write
	STATUS     current
	DESCRIPTION 
		"This parameter represents the key 4 used for wireless security 
		                 configuration. The key lengths 5/13/16 in ASCII or 10/26/32
		                 in HEXADECIMAL configures the WEP(64/128/152-bit) encryption respectively. 
		                 The key lengths 16 in ASCII or 32 in HEXADECIMAL configures the 
		                 TKIP(128-bit) or AES-CCM(128-bit) encryption."
	::= { wirelessSecurityCfgTableEntry 14 }

wirelessSecurityProfileGroupType  OBJECT-TYPE
	SYNTAX     INTEGER {
		none (1),
		worp (2),
		ap (3),
		mesh (4)
	}
	MAX-ACCESS read-write
	STATUS     current
	DESCRIPTION 
		"This table is used to specify  profile group type."
	::= { wirelessSecurityCfgTableEntry 15 }

-- ======================================================================================
-- RADIUS Security Subgroup Objects : radius
-- ======================================================================================
-- Radius Server profile Table

radiusSrvProfileTable  OBJECT-TYPE
	SYNTAX SEQUENCE OF RadiusSrvProfileTableEntry
	MAX-ACCESS not-accessible
	STATUS     current
	DESCRIPTION 
		"This table contains the radius server configuration profiles."
	::= { radius 1 }

radiusSrvProfileTableEntry  OBJECT-TYPE
	SYNTAX 	RadiusSrvProfileTableEntry
	MAX-ACCESS not-accessible
	STATUS     current
	DESCRIPTION 
		"This parameter represents the entry for the radius server profile table."
	INDEX { radiusSrvProfileTableIndex, 
		radiusSrvProfileTableSecIndex }
	::= { radiusSrvProfileTable 1 }

RadiusSrvProfileTableEntry ::= SEQUENCE {
	radiusSrvProfileTableIndex
		Unsigned32,
	radiusSrvProfileTableSecIndex
		Unsigned32,
	radiusSrvProfileType
		INTEGER,
	radiusSrvIPADDR
		IpAddress,
	radiusSrvServerPort
		Unsigned32,
	radiusSrvProfileServerSharedSecret
		DisplayString,
	radiusSrvProfileTableEntryStatus
		RowStatus,
	radiusSrvInetADDR
		InetAddress
}

radiusSrvProfileTableIndex  OBJECT-TYPE
	SYNTAX     Unsigned32 (1..16)
	MAX-ACCESS read-only
	STATUS     current
	DESCRIPTION 
		"This parameter represents the user defined profiles for RADIUS Server. "
	::= { radiusSrvProfileTableEntry 1 }

radiusSrvProfileTableSecIndex  OBJECT-TYPE
	SYNTAX     Unsigned32 (1..4)
	MAX-ACCESS read-only
	STATUS     current
	DESCRIPTION 
		"This parameter represents the user defined secondary profiles for RADIUS server.
		  Maximum profiles are 4."
	::= { radiusSrvProfileTableEntry 2 }

radiusSrvProfileType  OBJECT-TYPE
	SYNTAX     INTEGER {
		primaryAuthticationServer (1),
		secondaryAuthenticationServer (2),
		primaryAccountingServer (3),
		secondaryAccountingServer (4)
	}
	MAX-ACCESS read-only
	STATUS     current
	DESCRIPTION 
		"This parameter represents the RADIUS Server profile type. Select 
		 (1) for Primary Authentication Server, 
		 (2) for Secondary Authentication Server, 
		 (3) for Primary Accounting Server, and 
		 (4) for Secondary Accounting Server."
	::= { radiusSrvProfileTableEntry 3 }

radiusSrvIPADDR  OBJECT-TYPE
	SYNTAX     IpAddress
	MAX-ACCESS read-write
	STATUS     deprecated
	DESCRIPTION 
		"This parameter is used to specify the RADIUS Server IP Address. 
		         Its default value is 169.254.128.133.
		         This is now deprecated.Instead use radiusSrvInetADDR"
	DEFVAL  { 'a9fe8085'H }
	::= { radiusSrvProfileTableEntry 4 }

radiusSrvServerPort  OBJECT-TYPE
	SYNTAX     Unsigned32
	MAX-ACCESS read-write
	STATUS     current
	DESCRIPTION 
		"This parameter represents the RADIUS server authentication port and 
		 the default value is 1812."
	DEFVAL  { 1812 }
	::= { radiusSrvProfileTableEntry 5 }

radiusSrvProfileServerSharedSecret  OBJECT-TYPE
	SYNTAX     DisplayString (SIZE(1..32))
	MAX-ACCESS read-write
	STATUS     current
	DESCRIPTION 
		"This parameter represents the shared secret between the RADIUS server
		 and client. It is logically treated as write-only and should return 
		 the information in asterisks."
	DEFVAL  { "public" }
	::= { radiusSrvProfileTableEntry 6 }

radiusSrvProfileTableEntryStatus  OBJECT-TYPE
	SYNTAX     RowStatus
	MAX-ACCESS read-write
	STATUS     current
	DESCRIPTION 
		"This parameter is used to configure the entry status of RADIUS
		 server profile table.
		 It can be configured as 
		                 active(enable) -1, 
		                 notInService(disable) - 2, 
		                 createAndGo(create row) -4, 
		                 destroy(delete) - 6"
	DEFVAL  { active }
	::= { radiusSrvProfileTableEntry 7 }

radiusSrvInetADDR  OBJECT-TYPE
	SYNTAX     InetAddress
	MAX-ACCESS read-write
	STATUS     current
	DESCRIPTION 
		"This parameter is used to specify the RADIUS Server Inet Address."
	::= { radiusSrvProfileTableEntry 8 }

-- Radius Support profile Table

radiusSupProfileTable  OBJECT-TYPE
	SYNTAX SEQUENCE OF RadiusSupProfileTableEntry
	MAX-ACCESS not-accessible
	STATUS     current
	DESCRIPTION 
		"This table contains the radius support profile table
		 configurations."
	::= { radius 2 }

radiusSupProfileTableEntry  OBJECT-TYPE
	SYNTAX 	RadiusSupProfileTableEntry
	MAX-ACCESS not-accessible
	STATUS     current
	DESCRIPTION 
		"This parameter represents the entry for the radius support 
		 profile table."
	INDEX { radiusSupProfileTableIndex }
	::= { radiusSupProfileTable 1 }

RadiusSupProfileTableEntry ::= SEQUENCE {
	radiusSupProfileTableIndex
		Unsigned32,
	radiusSupProfileName
		DisplayString,
	radiusSupProfileMaxReTransmissions
		Unsigned32,
	radiusSupProfileMsgResponseTime
		Unsigned32,
	radiusSupProfileReAuthenticationPeriod
		Unsigned32,
	radiusSupProfileTableEntryStatus
		RowStatus
}

radiusSupProfileTableIndex  OBJECT-TYPE
	SYNTAX     Unsigned32 (1)
	MAX-ACCESS read-only
	STATUS     current
	DESCRIPTION 
		"This parameter represents the index for the radius support 
		 profile table. Each index corresponds to the one profile name 
		 in the radius server profile table "
	::= { radiusSupProfileTableEntry 1 }

radiusSupProfileName  OBJECT-TYPE
	SYNTAX     DisplayString (SIZE(1..32))
	MAX-ACCESS read-write
	STATUS     current
	DESCRIPTION 
		"This parameter represents the RADIUS profile name, only one profile is supported."
	::= { radiusSupProfileTableEntry 2 }

radiusSupProfileMaxReTransmissions  OBJECT-TYPE
	SYNTAX     Unsigned32 (1..4)
	MAX-ACCESS read-write
	STATUS     current
	DESCRIPTION 
		"This parameter represents the number of times the radius request
		 message to be sent to RADIUS server after the expiry of response
		 time."
	::= { radiusSupProfileTableEntry 3 }

radiusSupProfileMsgResponseTime  OBJECT-TYPE
	SYNTAX     Unsigned32 (3..12)
	MAX-ACCESS read-write
	STATUS     current
	DESCRIPTION 
		"This parameter represents the wait time in the RADIUS client for
		 the response message from RADIUS server."
	DEFVAL  { 3 }
	::= { radiusSupProfileTableEntry 4 }

radiusSupProfileReAuthenticationPeriod  OBJECT-TYPE
	SYNTAX     Unsigned32 (900..65535)
	MAX-ACCESS read-write
	STATUS     current
	DESCRIPTION 
		"The parameter represents the time interval within which the 
		 reauthentication of the 802.1x enabled station happens."
	DEFVAL  { 900 }
	::= { radiusSupProfileTableEntry 5 }

radiusSupProfileTableEntryStatus  OBJECT-TYPE
	SYNTAX     RowStatus
	MAX-ACCESS read-write
	STATUS     current
	DESCRIPTION 
		"This parameter is used to configure the entry status of RADIUS
		 supported profile table.
		 It can be configured as 
		                 active(enable) -1, 
		                 notInService(disable) - 2"
	DEFVAL  { active }
	::= { radiusSupProfileTableEntry 6 }

-- ======================================================================================
-- MAC ACL Security Subgroup Objects : macacl
-- ======================================================================================
-- MACACL Profile Table

macaclProfileTable  OBJECT-TYPE
	SYNTAX SEQUENCE OF MacaclProfileTableEntry
	MAX-ACCESS not-accessible
	STATUS     current
	DESCRIPTION 
		"This table contains the MAC access control profile configurations."
	::= { macacl 1 }

macaclProfileTableEntry  OBJECT-TYPE
	SYNTAX 	MacaclProfileTableEntry
	MAX-ACCESS not-accessible
	STATUS     current
	DESCRIPTION 
		"This parameter represents the entry for the MAC access control profile table."
	INDEX { macaclProfileTableIndex }
	::= { macaclProfileTable 1 }

MacaclProfileTableEntry ::= SEQUENCE {
	macaclProfileTableIndex
		Unsigned32,
	macaclProfileName
		DisplayString,
	macaclOperationType
		INTEGER,
	macaclTableEntryStatus
		RowStatus
}

macaclProfileTableIndex  OBJECT-TYPE
	SYNTAX     Unsigned32 (1..16)
	MAX-ACCESS read-only
	STATUS     current
	DESCRIPTION 
		"User defined profiles for MAC Access Control List. Max. number of profiles 
		 are 16."
	::= { macaclProfileTableEntry 1 }

macaclProfileName  OBJECT-TYPE
	SYNTAX     DisplayString (SIZE(1..32))
	MAX-ACCESS read-write
	STATUS     current
	DESCRIPTION 
		"This parameter represents the unique name MAC ACL profile."
	::= { macaclProfileTableEntry 2 }

macaclOperationType  OBJECT-TYPE
	SYNTAX     INTEGER {
		allow (1),
		deny (2)
	}
	MAX-ACCESS read-write
	STATUS     current
	DESCRIPTION 
		"This parameter is used o configure the type of MAC ACL profile. Select 
		(1) to allow and 
		(2) to deny."
	DEFVAL  { deny }
	::= { macaclProfileTableEntry 3 }

macaclTableEntryStatus  OBJECT-TYPE
	SYNTAX     RowStatus
	MAX-ACCESS read-create
	STATUS     current
	DESCRIPTION 
		"This parameter is used to configure the status of the security MAC ACL profile. 
		 It can be configured as 
		                 active(enable) -1, 
		                 notInService(disable) - 2, 
		                 createAndGo(create row) -4, 
		                 destroy(delete) - 6"
	DEFVAL  { active }
	::= { macaclProfileTableEntry 4 }

-- MACACL Address Table

macaclAddrTable  OBJECT-TYPE
	SYNTAX SEQUENCE OF MacaclAddrTableEntry
	MAX-ACCESS not-accessible
	STATUS     current
	DESCRIPTION 
		"This table holds MAC access control list addresses."
	::= { macacl 2 }

macaclAddrTableEntry  OBJECT-TYPE
	SYNTAX 	MacaclAddrTableEntry
	MAX-ACCESS not-accessible
	STATUS     current
	DESCRIPTION 
		"This parameter represents the entry for the MAC access control list address table."
	INDEX { macaclAddrTableIndex, 
		macaclAddrTableSecIndex }
	::= { macaclAddrTable 1 }

MacaclAddrTableEntry ::= SEQUENCE {
	macaclAddrTableIndex
		Unsigned32,
	macaclAddrTableSecIndex
		Unsigned32,
	macaclAddrTableMACAddress
		MacAddress,
	macaclAddrComment
		DisplayString,
	macaclAddrTableEntryStatus
		RowStatus
}

macaclAddrTableIndex  OBJECT-TYPE
	SYNTAX     Unsigned32 (1..16)
	MAX-ACCESS read-only
	STATUS     current
	DESCRIPTION 
		"This parameter represents the user defined profiles for MAC ACL Address. 
		 Max. profiles are 16 profiles."
	::= { macaclAddrTableEntry 1 }

macaclAddrTableSecIndex  OBJECT-TYPE
	SYNTAX     Unsigned32 (1..64)
	MAX-ACCESS read-only
	STATUS     current
	DESCRIPTION 
		"This parameter represents the user defined secondary profiles for MAC ACL Address.
		 Maximum entries are 64 -- one entry per station"
	::= { macaclAddrTableEntry 2 }

macaclAddrTableMACAddress  OBJECT-TYPE
	SYNTAX     MacAddress
	MAX-ACCESS read-write
	STATUS     current
	DESCRIPTION 
		"This parameter represents the valid MAC address for MAC ACL."
	::= { macaclAddrTableEntry 3 }

macaclAddrComment  OBJECT-TYPE
	SYNTAX     DisplayString (SIZE(0..32))
	MAX-ACCESS read-write
	STATUS     current
	DESCRIPTION 
		"This parameter displays a valid comment for MAC ACL Address."
	::= { macaclAddrTableEntry 4 }

macaclAddrTableEntryStatus  OBJECT-TYPE
	SYNTAX     RowStatus
	MAX-ACCESS read-create
	STATUS     current
	DESCRIPTION 
		"This parameter is used to configure the status of the security MAC ACL Address.
		 It can be configured as 
		                 active(enable) -1, 
		                 notInService(disable) - 2, 
		                 createAndGo(create row) -4, 
		                 destroy(delete) - 6"
	DEFVAL  { notInService }
	::= { macaclAddrTableEntry 5 }

-- ======================================================================================
-- QoS Group Objects
-- ======================================================================================
-- QoS Profile Table

qosProfileTable  OBJECT-TYPE
	SYNTAX SEQUENCE OF QosProfileTableEntry
	MAX-ACCESS not-accessible
	STATUS     current
	DESCRIPTION 
		"This table holds the various profiles for QOS (quality of service) configuration."
	::= { qos 1 }

qosProfileTableEntry  OBJECT-TYPE
	SYNTAX 	QosProfileTableEntry
	MAX-ACCESS not-accessible
	STATUS     current
	DESCRIPTION 
		"This parameter represents the entry for the qos profile table.This table
		 supports one entry."
	INDEX { qosProfileTableIndex }
	::= { qosProfileTable 1 }

QosProfileTableEntry ::= SEQUENCE {
	qosProfileTableIndex
		Unsigned32,
	qosProfileName
		DisplayString,
	qosProfileTablePolicyName
		DisplayString,
	qosProfileEDCAProfileName
		DisplayString,
	qosProfileTableQoSNACKStatus
		INTEGER
}

qosProfileTableIndex  OBJECT-TYPE
	SYNTAX     Unsigned32 (1)
	MAX-ACCESS read-only
	STATUS     current
	DESCRIPTION 
		"This parameter represents user defined profiles for Quality of Service (QoS)."
	::= { qosProfileTableEntry 1 }

qosProfileName  OBJECT-TYPE
	SYNTAX     DisplayString (SIZE(1..32))
	MAX-ACCESS read-write
	STATUS     current
	DESCRIPTION 
		"This parameter displays the name of the QoS profile that has been assigned."
	::= { qosProfileTableEntry 2 }

qosProfileTablePolicyName  OBJECT-TYPE
	SYNTAX     DisplayString (SIZE(1..32))
	MAX-ACCESS read-write
	STATUS     current
	DESCRIPTION 
		"This parameter displays the QoS Policy profile name."
	::= { qosProfileTableEntry 3 }

qosProfileEDCAProfileName  OBJECT-TYPE
	SYNTAX     DisplayString (SIZE(1..32))
	MAX-ACCESS read-write
	STATUS     current
	DESCRIPTION 
		"This parameter displays the name for QoS EDCA profile."
	::= { qosProfileTableEntry 4 }

qosProfileTableQoSNACKStatus  OBJECT-TYPE
	SYNTAX     INTEGER {
		enable (1),
		disable (2)
	}
	MAX-ACCESS read-write
	STATUS     current
	DESCRIPTION 
		"This parameter is used to configure the status of the QoS profile ACK. "
	::= { qosProfileTableEntry 5 }

-- QoS Policy Table

qoSPolicyTable  OBJECT-TYPE
	SYNTAX SEQUENCE OF QoSPolicyTableEntry
	MAX-ACCESS not-accessible
	STATUS     current
	DESCRIPTION 
		"This table contains the QOS policy configurations."
	::= { qos 2 }

qoSPolicyTableEntry  OBJECT-TYPE
	SYNTAX 	QoSPolicyTableEntry
	MAX-ACCESS not-accessible
	STATUS     current
	DESCRIPTION 
		"This parameter represents the entry for the qos policy table."
	INDEX { qoSPolicyTableIndex, 
		qoSPolicyTableSecIndex }
	::= { qoSPolicyTable 1 }

QoSPolicyTableEntry ::= SEQUENCE {
	qoSPolicyTableIndex
		Unsigned32,
	qoSPolicyTableSecIndex
		Unsigned32,
	qoSPolicyTablePolicyName
		DisplayString,
	qoSPolicyType
		INTEGER,
	qoSPolicyPriorityMapping
		Unsigned32,
	qoSPolicyMarkingStatus
		INTEGER,
	qoSPolicyTableEntryStatus
		RowStatus
}

qoSPolicyTableIndex  OBJECT-TYPE
	SYNTAX     Unsigned32 (1)
	MAX-ACCESS read-only
	STATUS     current
	DESCRIPTION 
		"This parameter represents user defined profiles for QoS Policy list."
	::= { qoSPolicyTableEntry 1 }

qoSPolicyTableSecIndex  OBJECT-TYPE
	SYNTAX     Unsigned32 (1..4)
	MAX-ACCESS read-only
	STATUS     current
	DESCRIPTION 
		"This parameter represents user defined secondary profiles. They are 
		 inbound layer2 -1, 
		 inbound layer3 -2, 
		 outbound layer2 -3 and
		 outbound layer3 -4"
	::= { qoSPolicyTableEntry 2 }

qoSPolicyTablePolicyName  OBJECT-TYPE
	SYNTAX     DisplayString
	MAX-ACCESS read-only
	STATUS     current
	DESCRIPTION 
		"This parameter displays the QoS policy name."
	::= { qoSPolicyTableEntry 3 }

qoSPolicyType  OBJECT-TYPE
	SYNTAX     INTEGER {
		inboundLayer2 (1),
		inboundLayer3 (2),
		outboundLayer2 (3),
		outboundLayer3 (4)
	}
	MAX-ACCESS read-only
	STATUS     current
	DESCRIPTION 
		"This parameter configures the QoS Policy type. They can be configured
		 as the following: 
		 inbound layer2(1), 
		 inbound layer3(2), 
		 outbound layer2(3) and  
		 outbound layer3(4)"
	::= { qoSPolicyTableEntry 4 }

qoSPolicyPriorityMapping  OBJECT-TYPE
	SYNTAX     Unsigned32 (1..16)
	MAX-ACCESS read-write
	STATUS     current
	DESCRIPTION 
		"This parameter is used as the primary index to the QoS 802.1D to 802.1p 
		 mapping table. "
	::= { qoSPolicyTableEntry 5 }

qoSPolicyMarkingStatus  OBJECT-TYPE
	SYNTAX     INTEGER {
		enable (1),
		disable (2),
		notSupported (3)
	}
	MAX-ACCESS read-write
	STATUS     current
	DESCRIPTION 
		"This parameter is used to enable or disable QoS Policy markings. Select 
		 (1) to enable, 
		 (2) to disable, and 
		 (3) for not supported option."
	::= { qoSPolicyTableEntry 6 }

qoSPolicyTableEntryStatus  OBJECT-TYPE
	SYNTAX     RowStatus
	MAX-ACCESS read-create
	STATUS     current
	DESCRIPTION 
		"The parameter is used to configure the QoS Policy Table status.
		 It can be configured as 
		                 active(enable) -1, 
		                 notInService(disable) - 2, 
		                 createAndGo(create row) -4, 
		                 destroy(delete) - 6"
	::= { qoSPolicyTableEntry 7 }

-- ======================================================================================
-- Wireless QoS Subgroup Objects : 
-- ======================================================================================
-- Wireless QoS EDCA Table

wirelessQoSEDCATable  OBJECT-TYPE
	SYNTAX SEQUENCE OF WirelessQoSEDCATableEntry
	MAX-ACCESS not-accessible
	STATUS     current
	DESCRIPTION 
		"This table holds the wireless QOS EDCA (enhanced distributed channel access)
		 configurations."
	::= { wirelessQoS 1 }

wirelessQoSEDCATableEntry  OBJECT-TYPE
	SYNTAX 	WirelessQoSEDCATableEntry
	MAX-ACCESS not-accessible
	STATUS     current
	DESCRIPTION 
		"This parameter represents the entry for the wireless QOS EDCA table."
	INDEX { wirelessQoSEDCATableIndex, 
		wirelessQoSEDCATableSecIndex }
	::= { wirelessQoSEDCATable 1 }

WirelessQoSEDCATableEntry ::= SEQUENCE {
	wirelessQoSEDCATableIndex
		Unsigned32,
	wirelessQoSEDCATableSecIndex
		Unsigned32,
	wirelessQoSEDCATableProfileName
		DisplayString,
	wirelessQoSEDCATableCWmin
		Unsigned32,
	wirelessQoSEDCATableCWmax
		Unsigned32,
	wirelessQoSEDCATableAIFSN
		Unsigned32,
	wirelessQoSEDCATableTXOP
		DisplayString,
	wirelessQoSEDCATableACM
		INTEGER,
	wirelessQoSEDCATableAPCWmin
		Unsigned32,
	wirelessQoSEDCATableAPCWmax
		Unsigned32,
	wirelessQoSEDCATableAPAIFSN
		Unsigned32,
	wirelessQoSEDCATableAPTXOP
		DisplayString,
	wirelessQoSEDCATableAPACM
		INTEGER
}

wirelessQoSEDCATableIndex  OBJECT-TYPE
	SYNTAX     Unsigned32 (1)
	MAX-ACCESS read-only
	STATUS     current
	DESCRIPTION 
		"This parameter is user defined profiles for Wireless QoS EDCA. 
		 Max profile that user can define is 1."
	::= { wirelessQoSEDCATableEntry 1 }

wirelessQoSEDCATableSecIndex  OBJECT-TYPE
	SYNTAX     Unsigned32 (1..4)
	MAX-ACCESS read-only
	STATUS     current
	DESCRIPTION 
		"This parameter represents the user defined secondary profiles for Wireless QoS EDCA. 
		 Maximum profiles are 4.  
		 BK -1 (back ground), 
		 BE -2 (best effort), 
		 VI -3 (video), 
		 VO -4 (voice)"
	::= { wirelessQoSEDCATableEntry 2 }

wirelessQoSEDCATableProfileName  OBJECT-TYPE
	SYNTAX     DisplayString (SIZE(1..32))
	MAX-ACCESS read-write
	STATUS     current
	DESCRIPTION 
		"This parameter displays the name for the Wireless QoS EDCA profile."
	::= { wirelessQoSEDCATableEntry 3 }

wirelessQoSEDCATableCWmin  OBJECT-TYPE
	SYNTAX     Unsigned32 (0..32767)
	MAX-ACCESS read-write
	STATUS     current
	DESCRIPTION 
		"This parameter is used to configure the CW(Contention Window) min value 
		 for the wireless QoS EDCA profile. It can be configured up to 255 value.
		 If this value is configured lower, then this increases the priority of 
		 the access category."
	::= { wirelessQoSEDCATableEntry 4 }

wirelessQoSEDCATableCWmax  OBJECT-TYPE
	SYNTAX     Unsigned32 (0..32767)
	MAX-ACCESS read-write
	STATUS     current
	DESCRIPTION 
		"This parameter is used to configure the CW(Contention window) Max value
		 for the wireless QoS EDCA profile. This value can be configured up to 
		 65535. If this value id confiured to a lower value, then this increases 
		 the priority of access category."
	::= { wirelessQoSEDCATableEntry 5 }

wirelessQoSEDCATableAIFSN  OBJECT-TYPE
	SYNTAX     Unsigned32 (2..15)
	MAX-ACCESS read-write
	STATUS     current
	DESCRIPTION 
		"This parameter is used to configure the AIFSN (Arbitrary Inter Frame 
		 Space Number) value for the wireless QoS EDCA profile. It can be 
		 configured up to 15. If this value is configured lower,then this 
		 increases the priority of the access category."
	::= { wirelessQoSEDCATableEntry 6 }

wirelessQoSEDCATableTXOP  OBJECT-TYPE
	SYNTAX     DisplayString (SIZE(1..32))
	MAX-ACCESS read-write
	STATUS     current
	DESCRIPTION 
		"This parameter is used to configure TXOP(transmission oppurtunities)
		 value for Wireless QoS EDCA. The values can be configured up to 65535.
		 If this value for this parameter is configured lower, then this 
		 decreases the priority of the access category."
	::= { wirelessQoSEDCATableEntry 7 }

wirelessQoSEDCATableACM  OBJECT-TYPE
	SYNTAX     INTEGER {
		enable (1),
		disable (2)
	}
	MAX-ACCESS read-write
	STATUS     current
	DESCRIPTION 
		"This parameter is used to enable or disable the value for Addmission 
		 Control Mandatory. If ACM value is set to enable for a particular 
		 access category, then certain procedures needs to followed for using 
		 that access category."
	::= { wirelessQoSEDCATableEntry 8 }

wirelessQoSEDCATableAPCWmin  OBJECT-TYPE
	SYNTAX     Unsigned32 (0..32767)
	MAX-ACCESS read-write
	STATUS     current
	DESCRIPTION 
		"This parameter is used to configure the minimum value for APCWmin. 
		 It can be configured upto 32767. "
	::= { wirelessQoSEDCATableEntry 9 }

wirelessQoSEDCATableAPCWmax  OBJECT-TYPE
	SYNTAX     Unsigned32 (0..32767)
	MAX-ACCESS read-write
	STATUS     current
	DESCRIPTION 
		"This parameter is used to configure the  maximum value for APCWmax. 
		 It can be configured upto 32767. "
	::= { wirelessQoSEDCATableEntry 10 }

wirelessQoSEDCATableAPAIFSN  OBJECT-TYPE
	SYNTAX     Unsigned32 (1..15)
	MAX-ACCESS read-write
	STATUS     current
	DESCRIPTION 
		"This parameter is used to configure the value fo APAIFSN(Arbitration 
		Inter-Frame Space Number). The value for the APAIFSN can be configured up to 15"
	::= { wirelessQoSEDCATableEntry 11 }

wirelessQoSEDCATableAPTXOP  OBJECT-TYPE
	SYNTAX     DisplayString (SIZE(1..32))
	MAX-ACCESS read-write
	STATUS     current
	DESCRIPTION 
		"This parameter is used to configure the APTXOP (transmission oppurtunities)
		 for the QoS EDCA profile. If the value is set to 0, then only one MPDU or 
		 MSDU can be transmitted"
	::= { wirelessQoSEDCATableEntry 12 }

wirelessQoSEDCATableAPACM  OBJECT-TYPE
	SYNTAX     INTEGER {
		enable (1),
		disable (2)
	}
	MAX-ACCESS read-write
	STATUS     current
	DESCRIPTION 
		"This parameter is used to configure the APACM for the QoS EDCA profile. 
		 Select (1) to enable the profile and 
		        (2) to disable it."
	::= { wirelessQoSEDCATableEntry 13 }

-- ======================================================================================
-- L2L3 QoS Subgroup Objects : l2QoS
-- ======================================================================================
-- L2L23 QoS Dot1D to Dot1p Mapping Table

l2l3QoSDot1DToDot1pMappingTable  OBJECT-TYPE
	SYNTAX SEQUENCE OF L2l3QoSDot1DToDot1pMappingTableEntry
	MAX-ACCESS not-accessible
	STATUS     current
	DESCRIPTION 
		"This table is used to configure Quality of Service mappings between 
		         802.1D and 802.1p priorities."
	::= { l2l3QoS 1 }

l2l3QoSDot1DToDot1pMappingTableEntry  OBJECT-TYPE
	SYNTAX 	L2l3QoSDot1DToDot1pMappingTableEntry
	MAX-ACCESS not-accessible
	STATUS     current
	DESCRIPTION 
		"This parameter represents entries in the QoS 802.1D to 802.1p Mapping  
		         Table."
	INDEX { l2l3QoSDot1DToDot1pMappingTableIndex, 
		l2l3QoSDot1dPriority }
	::= { l2l3QoSDot1DToDot1pMappingTable 1 }

L2l3QoSDot1DToDot1pMappingTableEntry ::= SEQUENCE {
	l2l3QoSDot1DToDot1pMappingTableIndex
		Unsigned32,
	l2l3QoSDot1dPriority
		Unsigned32,
	l2l3QoSDot1pPriority
		Unsigned32
}

l2l3QoSDot1DToDot1pMappingTableIndex  OBJECT-TYPE
	SYNTAX     Unsigned32 (1)
	MAX-ACCESS read-only
	STATUS     current
	DESCRIPTION 
		"This parameter is used as the primary index to the QoS 802.1D to 802.1p 
		         mapping table. This is based on the QoS profile."
	::= { l2l3QoSDot1DToDot1pMappingTableEntry 1 }

l2l3QoSDot1dPriority  OBJECT-TYPE
	SYNTAX     Unsigned32 (1..8)
	MAX-ACCESS read-only
	STATUS     current
	DESCRIPTION 
		"This parameter is used to specify the 802.1d priority and is used as  
		         the secondary index to the 802.1D to 802.1p mapping table."
	::= { l2l3QoSDot1DToDot1pMappingTableEntry 2 }

l2l3QoSDot1pPriority  OBJECT-TYPE
	SYNTAX     Unsigned32 (0..7)
	MAX-ACCESS read-write
	STATUS     current
	DESCRIPTION 
		"This parameter is used to specify the 802.1D priority to be mapped to a 
		                  802.1p priority"
	::= { l2l3QoSDot1DToDot1pMappingTableEntry 3 }

-- L2 QoS Dot1D to IPDSCP Mapping Table

l2l3QoSDot1DToIPDSCPMappingTable  OBJECT-TYPE
	SYNTAX SEQUENCE OF L2l3QoSDot1DToIPDSCPMappingTableEntry
	MAX-ACCESS not-accessible
	STATUS     current
	DESCRIPTION 
		"This table is used to configure Quality of Service mappings between 
		         802.1D to IP DSCP (Differentiated Services Code Point) priorities."
	::= { l2l3QoS 2 }

l2l3QoSDot1DToIPDSCPMappingTableEntry  OBJECT-TYPE
	SYNTAX 	L2l3QoSDot1DToIPDSCPMappingTableEntry
	MAX-ACCESS not-accessible
	STATUS     current
	DESCRIPTION 
		"This parameter represents entries in the 802.1D to IP DSCP Mapping  
		         Table."
	INDEX { l2l3QoSDot1DToIPDSCPMappingTableIndex, 
		l2l3QoSDot1dPriorityIPDSCP }
	::= { l2l3QoSDot1DToIPDSCPMappingTable 1 }

L2l3QoSDot1DToIPDSCPMappingTableEntry ::= SEQUENCE {
	l2l3QoSDot1DToIPDSCPMappingTableIndex
		Unsigned32,
	l2l3QoSDot1dPriorityIPDSCP
		Unsigned32,
	l2l3QoSDSCPPriorityLowerLimit
		Unsigned32,
	l2l3QoSDSCPPriorityUpperLimit
		Unsigned32
}

l2l3QoSDot1DToIPDSCPMappingTableIndex  OBJECT-TYPE
	SYNTAX     Unsigned32 (1..16)
	MAX-ACCESS read-only
	STATUS     current
	DESCRIPTION 
		"This parameter is used as the primary index to the 802.1D to IP DSCP 
		         mapping table."
	::= { l2l3QoSDot1DToIPDSCPMappingTableEntry 1 }

l2l3QoSDot1dPriorityIPDSCP  OBJECT-TYPE
	SYNTAX     Unsigned32 (0..7)
	MAX-ACCESS read-only
	STATUS     current
	DESCRIPTION 
		"This parameter is used to specify the 802.1D priority and is used as  
		         the secondary index to the 802.1D to IP DSCP mapping table."
	::= { l2l3QoSDot1DToIPDSCPMappingTableEntry 2 }

l2l3QoSDSCPPriorityLowerLimit  OBJECT-TYPE
	SYNTAX     Unsigned32 (0..63)
	MAX-ACCESS read-write
	STATUS     current
	DESCRIPTION 
		"This parameter is used to specify IP DSCP lower limit."
	::= { l2l3QoSDot1DToIPDSCPMappingTableEntry 3 }

l2l3QoSDSCPPriorityUpperLimit  OBJECT-TYPE
	SYNTAX     Unsigned32 (0..63)
	MAX-ACCESS read-write
	STATUS     current
	DESCRIPTION 
		"This parameter is used to specify IP DSCP upper limit."
	::= { l2l3QoSDot1DToIPDSCPMappingTableEntry 4 }

-- ======================================================================================
-- WORP QoS Subgroup Objects : worpQoS
-- ======================================================================================
-- - WORP QoS PIR MAC Table Group

worpQoSPIRMacTable  OBJECT-TYPE
	SYNTAX SEQUENCE OF WorpQoSPIRMacTableEntry
	MAX-ACCESS not-accessible
	STATUS     current
	DESCRIPTION 
		"This Table holds the MAC Address details for Packet Identification Rule Clasification."
	::= { worpQoS 1 }

worpQoSPIRMacTableEntry  OBJECT-TYPE
	SYNTAX 	WorpQoSPIRMacTableEntry
	MAX-ACCESS not-accessible
	STATUS     current
	DESCRIPTION 
		"This parameter represents the entry for the worpQoSPIRMacTable."
	INDEX { worpQoSPIRMacTableIndex }
	::= { worpQoSPIRMacTable 1 }

WorpQoSPIRMacTableEntry ::= SEQUENCE {
	worpQoSPIRMacTableIndex
		Unsigned32,
	worpQoSPIRMacAddr
		MacAddress,
	worpQoSPIRMacMask
		MacAddress,
	worpQoSPIRMacComment
		DisplayString,
	worpQoSPIRMacTableEntryStatus
		RowStatus
}

worpQoSPIRMacTableIndex  OBJECT-TYPE
	SYNTAX     Unsigned32 (1..256)
	MAX-ACCESS read-only
	STATUS     current
	DESCRIPTION 
		"This parameter specifies the index number of the entry in the table."
	::= { worpQoSPIRMacTableEntry 1 }

worpQoSPIRMacAddr  OBJECT-TYPE
	SYNTAX     MacAddress
	MAX-ACCESS read-write
	STATUS     current
	DESCRIPTION 
		"This parameter specifies the MAC Address which can be used for PIR 
		                  classification."
	::= { worpQoSPIRMacTableEntry 2 }

worpQoSPIRMacMask  OBJECT-TYPE
	SYNTAX     MacAddress
	MAX-ACCESS read-write
	STATUS     current
	DESCRIPTION 
		"This parameter specifies the MAC Address mask for the worpQoSPIRMacAddr."
	::= { worpQoSPIRMacTableEntry 3 }

worpQoSPIRMacComment  OBJECT-TYPE
	SYNTAX     DisplayString
	MAX-ACCESS read-write
	STATUS     current
	DESCRIPTION 
		"This parameter specifies the comment for the mac entry."
	DEFVAL  { "default-mac" }
	::= { worpQoSPIRMacTableEntry 4 }

worpQoSPIRMacTableEntryStatus  OBJECT-TYPE
	SYNTAX     RowStatus
	MAX-ACCESS read-write
	STATUS     current
	DESCRIPTION 
		"This parameter is used to configure the worpQoSPIRMacTable status. 
		 It can be configured as 
		                 active(enable) -1, 
		                 notInService(disable) - 2, 
		                 createAndGo(create row) -4, 
		                 destroy(delete) - 6"
	DEFVAL  { active }
	::= { worpQoSPIRMacTableEntry 5 }

-- - WORP QoS PIR IP Address Table Group

worpQoSPIRIPTable  OBJECT-TYPE
	SYNTAX SEQUENCE OF WorpQoSPIRIPTableEntry
	MAX-ACCESS not-accessible
	STATUS     current
	DESCRIPTION 
		"This Table holds the IP Address details for PIR (Packet Identification Rule) Clasification."
	::= { worpQoS 2 }

worpQoSPIRIPTableEntry  OBJECT-TYPE
	SYNTAX 	WorpQoSPIRIPTableEntry
	MAX-ACCESS not-accessible
	STATUS     current
	DESCRIPTION 
		"This parameter represents the entry for the worpQoSPIRIPTable."
	INDEX { worpQoSPIRIPTableIndex }
	::= { worpQoSPIRIPTable 1 }

WorpQoSPIRIPTableEntry ::= SEQUENCE {
	worpQoSPIRIPTableIndex
		Unsigned32,
	worpQoSPIRIPAddr
		IpAddress,
	worpQoSPIRIPSubMask
		IpAddress,
	worpQoSPIRIPComment
		DisplayString,
	worpQoSPIRIPTableEntryStatus
		RowStatus
}

worpQoSPIRIPTableIndex  OBJECT-TYPE
	SYNTAX     Unsigned32 (1..256)
	MAX-ACCESS read-only
	STATUS     current
	DESCRIPTION 
		"This parameter specifies the index number of the entry in the table."
	::= { worpQoSPIRIPTableEntry 1 }

worpQoSPIRIPAddr  OBJECT-TYPE
	SYNTAX     IpAddress
	MAX-ACCESS read-write
	STATUS     current
	DESCRIPTION 
		"This parameter specifies the IP Address which can be used for PIR 
		                  classification."
	::= { worpQoSPIRIPTableEntry 2 }

worpQoSPIRIPSubMask  OBJECT-TYPE
	SYNTAX     IpAddress
	MAX-ACCESS read-write
	STATUS     current
	DESCRIPTION 
		"This parameter specifies the Subnet Mask for the worpQoSPIRIPAddr."
	DEFVAL  { 'ffffffff'H }
	::= { worpQoSPIRIPTableEntry 3 }

worpQoSPIRIPComment  OBJECT-TYPE
	SYNTAX     DisplayString
	MAX-ACCESS read-write
	STATUS     current
	DESCRIPTION 
		"This parameter specifies the comment for the IP Address entry."
	DEFVAL  { "default-ip" }
	::= { worpQoSPIRIPTableEntry 4 }

worpQoSPIRIPTableEntryStatus  OBJECT-TYPE
	SYNTAX     RowStatus
	MAX-ACCESS read-write
	STATUS     current
	DESCRIPTION 
		"This parameter is used to configure the worpQoSPIRIPTable status. 
		 It can be configured as 
		                 active(enable) -1, 
		                 notInService(disable) - 2, 
		                 createAndGo(create row) -4, 
		                 destroy(delete) - 6"
	DEFVAL  { active }
	::= { worpQoSPIRIPTableEntry 5 }

-- - WORP QoS PIR Port Table Group

worpQoSPIRPortTable  OBJECT-TYPE
	SYNTAX SEQUENCE OF WorpQoSPIRPortTableEntry
	MAX-ACCESS not-accessible
	STATUS     current
	DESCRIPTION 
		"This Table holds the TCP/UDP Port details for PIR (Packet Identification Rule) 
		                 Clasification."
	::= { worpQoS 3 }

worpQoSPIRPortTableEntry  OBJECT-TYPE
	SYNTAX 	WorpQoSPIRPortTableEntry
	MAX-ACCESS not-accessible
	STATUS     current
	DESCRIPTION 
		"This parameter represents the entry for the worpQoSPIRPortTable."
	INDEX { worpQoSPIRPortTableIndex }
	::= { worpQoSPIRPortTable 1 }

WorpQoSPIRPortTableEntry ::= SEQUENCE {
	worpQoSPIRPortTableIndex
		Unsigned32,
	worpQoSPIRStartPort
		Unsigned32,
	worpQoSPIREndPort
		Unsigned32,
	worpQoSPIRPortComment
		DisplayString,
	worpQoSPIRPortTableEntryStatus
		RowStatus
}

worpQoSPIRPortTableIndex  OBJECT-TYPE
	SYNTAX     Unsigned32 (1..256)
	MAX-ACCESS read-only
	STATUS     current
	DESCRIPTION 
		"This parameter specifies the index number of the entry in the table."
	::= { worpQoSPIRPortTableEntry 1 }

worpQoSPIRStartPort  OBJECT-TYPE
	SYNTAX     Unsigned32 (1..65535)
	MAX-ACCESS read-write
	STATUS     current
	DESCRIPTION 
		"This parameter specifies the Starting TCP/UDP Port Number which can be used for PIR 
		                  classification."
	::= { worpQoSPIRPortTableEntry 2 }

worpQoSPIREndPort  OBJECT-TYPE
	SYNTAX     Unsigned32 (1..65535)
	MAX-ACCESS read-write
	STATUS     current
	DESCRIPTION 
		"This parameter specifies the Ending TCP/UDP Port Number which can be used for PIR 
		                  classification."
	::= { worpQoSPIRPortTableEntry 3 }

worpQoSPIRPortComment  OBJECT-TYPE
	SYNTAX     DisplayString
	MAX-ACCESS read-write
	STATUS     current
	DESCRIPTION 
		"This parameter specifies the comment for the TCP/UDP Port entry."
	DEFVAL  { "default-port" }
	::= { worpQoSPIRPortTableEntry 4 }

worpQoSPIRPortTableEntryStatus  OBJECT-TYPE
	SYNTAX     RowStatus
	MAX-ACCESS read-write
	STATUS     current
	DESCRIPTION 
		"This parameter is used to configure the worpQoSPIRPortTable status. 
		 It can be configured as 
		                 active(enable) -1, 
		                 notInService(disable) - 2, 
		                 createAndGo(create row) -4, 
		                 destroy(delete) - 6."
	DEFVAL  { active }
	::= { worpQoSPIRPortTableEntry 5 }

-- - WORP QoS PIR Mapping Table Group

worpQoSPIRMapTable  OBJECT-TYPE
	SYNTAX SEQUENCE OF WorpQoSPIRMapTableEntry
	MAX-ACCESS not-accessible
	STATUS     current
	DESCRIPTION 
		"This Table holds the Mapping information between PIR MAC Table entries, 
		                 PIR IP Table entries, PIR Port Table entries with PIR Table."
	::= { worpQoS 4 }

worpQoSPIRMapTableEntry  OBJECT-TYPE
	SYNTAX 	WorpQoSPIRMapTableEntry
	MAX-ACCESS not-accessible
	STATUS     current
	DESCRIPTION 
		"This table represents the entry for the worpQoSPIRMapTable."
	INDEX { worpQoSPIRMapTableIndex }
	::= { worpQoSPIRMapTable 1 }

WorpQoSPIRMapTableEntry ::= SEQUENCE {
	worpQoSPIRMapTableIndex
		Unsigned32,
	worpQoSPIRMapRuleName
		DisplayString,
	worpQoSPIRMapSrcMacIndexList
		DisplayString,
	worpQoSPIRMapDstMacIndexList
		DisplayString,
	worpQoSPIRMapSrcIpAddrIndexList
		DisplayString,
	worpQoSPIRMapDstIpAddrIndexList
		DisplayString,
	worpQoSPIRMapSrcPortIndexList
		DisplayString,
	worpQoSPIRMapDstPortIndexList
		DisplayString,
	worpQoSPIRMapSrcIpv6AddrIndexList
		DisplayString,
	worpQoSPIRMapDstIpv6AddrIndexList
		DisplayString
}

worpQoSPIRMapTableIndex  OBJECT-TYPE
	SYNTAX     Unsigned32 (1..256)
	MAX-ACCESS read-only
	STATUS     current
	DESCRIPTION 
		"This parameter specifies the index number of the entry in the table."
	::= { worpQoSPIRMapTableEntry 1 }

worpQoSPIRMapRuleName  OBJECT-TYPE
	SYNTAX     DisplayString
	MAX-ACCESS read-only
	STATUS     current
	DESCRIPTION 
		"This parameter specifies the PIR Rule name corresponds to this index."
	::= { worpQoSPIRMapTableEntry 2 }

worpQoSPIRMapSrcMacIndexList  OBJECT-TYPE
	SYNTAX     DisplayString
	MAX-ACCESS read-write
	STATUS     current
	DESCRIPTION 
		"This parameter specifies the Source MAC Address Classification for the 
		                 PIR Rule. This is a display string consists of index number of the PIR 
		                 MAC Table entries with comma seperated. Value 0 indicates that this list 
		                 is disabled."
	DEFVAL  { "0" }
	::= { worpQoSPIRMapTableEntry 3 }

worpQoSPIRMapDstMacIndexList  OBJECT-TYPE
	SYNTAX     DisplayString
	MAX-ACCESS read-write
	STATUS     current
	DESCRIPTION 
		"This parameter specifies the Destination MAC Address Classification for the 
		                 PIR Rule. This is a display string consists of index number of the PIR MAC 
		                 Table entries with comma seperated. Value 0 indicates that this list is disabled."
	DEFVAL  { "0" }
	::= { worpQoSPIRMapTableEntry 4 }

worpQoSPIRMapSrcIpAddrIndexList  OBJECT-TYPE
	SYNTAX     DisplayString
	MAX-ACCESS read-write
	STATUS     current
	DESCRIPTION 
		"This parameter specifies the Source IP Address Classification for the PIR Rule. 
		                 This is a display string consists of index number of the PIR IP Table entries 
		                 with comma seperated. Value 0 indicates that this list is disabled."
	DEFVAL  { "0" }
	::= { worpQoSPIRMapTableEntry 5 }

worpQoSPIRMapDstIpAddrIndexList  OBJECT-TYPE
	SYNTAX     DisplayString
	MAX-ACCESS read-write
	STATUS     current
	DESCRIPTION 
		"This parameter specifies the Destination IP Address Classification for the PIR Rule. 
		                 This is a display string consists of index number of the PIR IP Table entries with
		                 comma seperated. Value 0 indicates that this list is disabled."
	DEFVAL  { "0" }
	::= { worpQoSPIRMapTableEntry 6 }

worpQoSPIRMapSrcPortIndexList  OBJECT-TYPE
	SYNTAX     DisplayString
	MAX-ACCESS read-write
	STATUS     current
	DESCRIPTION 
		"This parameter specifies the Source TCP/UDP Port Classification for the PIR Rule. 
		                 This is a display string consists of index number of the PIR MAC Table entries with 
		                 comma seperated. Value 0 indicates that this list is disabled."
	DEFVAL  { "0" }
	::= { worpQoSPIRMapTableEntry 7 }

worpQoSPIRMapDstPortIndexList  OBJECT-TYPE
	SYNTAX     DisplayString
	MAX-ACCESS read-write
	STATUS     current
	DESCRIPTION 
		"This parameter specifies the Destination TCP/UDP Port Classification for the PIR Rule. 
		                 This is a display string consists of index number of the PIR MAC Table entries with 
		                 comma seperated. Value 0 indicates that this list is disabled."
	DEFVAL  { "0" }
	::= { worpQoSPIRMapTableEntry 8 }

worpQoSPIRMapSrcIpv6AddrIndexList  OBJECT-TYPE
	SYNTAX     DisplayString
	MAX-ACCESS read-write
	STATUS     current
	DESCRIPTION 
		"This parameter specifies the Source IPv6 Address Classification for the PIR Rule. 
		                 This is a display string consists of index number of the PIR Inet Table entries 
		                 with comma seperated. Value 0 indicates that this list is disabled."
	DEFVAL  { "0" }
	::= { worpQoSPIRMapTableEntry 9 }

worpQoSPIRMapDstIpv6AddrIndexList  OBJECT-TYPE
	SYNTAX     DisplayString
	MAX-ACCESS read-write
	STATUS     current
	DESCRIPTION 
		"This parameter specifies the Destination IPv6 Address Classification for the PIR Rule. 
		                 This is a display string consists of index number of the PIR Inet Table entries with
		                 comma seperated. Value 0 indicates that this list is disabled."
	DEFVAL  { "0" }
	::= { worpQoSPIRMapTableEntry 10 }

-- - WORP QoS PIR Rule Group

worpQoSPIRTable  OBJECT-TYPE
	SYNTAX SEQUENCE OF WorpQoSPIRTableEntry
	MAX-ACCESS not-accessible
	STATUS     current
	DESCRIPTION 
		"This Table holds the Packet Identification Rule(PIR) information for QoS feature."
	::= { worpQoS 5 }

worpQoSPIRTableEntry  OBJECT-TYPE
	SYNTAX 	WorpQoSPIRTableEntry
	MAX-ACCESS not-accessible
	STATUS     current
	DESCRIPTION 
		"This parameter represents the entry for the worpQoSPIRTable."
	INDEX { worpQoSPIRTableIndex }
	::= { worpQoSPIRTable 1 }

WorpQoSPIRTableEntry ::= SEQUENCE {
	worpQoSPIRTableIndex
		Unsigned32,
	worpQoSPIRRuleName
		DisplayString,
	worpQoSPIRRuleBitMask
		Unsigned32,
	worpQoSPIRIPToSLow
		Unsigned32,
	worpQoSPIRIPToSHigh
		Unsigned32,
	worpQoSPIRIPToSMask
		Unsigned32,
	worpQoSPIRIPProtocolIds
		DisplayString,
	worpQoSPIREtherPriorityLow
		Unsigned32,
	worpQoSPIREtherPriorityHigh
		Unsigned32,
	worpQoSPIRVlanId
		VlanId,
	worpQoSPIREtherType
		INTEGER,
	worpQoSPIREtherValue
		OCTET STRING,
	worpQoSPIRPPPoEEncapsulation
		INTEGER,
	worpQoSPIRPPPoEProtocolId
		OCTET STRING,
	worpQoSPIRMapTableIndexVal
		Unsigned32,
	worpQoSPIRTableEntryStatus
		RowStatus
}

worpQoSPIRTableIndex  OBJECT-TYPE
	SYNTAX     Unsigned32 (1..64)
	MAX-ACCESS read-only
	STATUS     current
	DESCRIPTION 
		"This parameter specifies the index number of the entry in the table."
	::= { worpQoSPIRTableEntry 1 }

worpQoSPIRRuleName  OBJECT-TYPE
	SYNTAX     DisplayString
	MAX-ACCESS read-write
	STATUS     current
	DESCRIPTION 
		"This parameter specifies the Packet Identification Rule(PIR) Name."
	DEFVAL  { "default-pir" }
	::= { worpQoSPIRTableEntry 2 }

worpQoSPIRRuleBitMask  OBJECT-TYPE
	SYNTAX     Unsigned32 (0..4095)
	MAX-ACCESS read-write
	STATUS     current
	DESCRIPTION 
		"This parameter specifies which Packet classification rules are enabled. It is a Bit Mask field. Bits are defined as follows 
		Bit0 - Dst MAC rule Enabled. 
		Bit1 - Src MAC rule Enabled. 
		Bit2 - Prity rule Enabled. 
		Bit3 - Vlan ID rule Enabled. 
		Bit4 - Ether value rule Enabled. 
		Bit5 - ToS rule Enabled. 
		Bit6 - IP PROTOCOL rule Enabled. 
		Bit7 - Dst IP Addr rule Enabled. 
		Bit8 - Src IP Addr rule Enabled. 
		Bit9 - Dst Port rule Enabled. 
		Bit10 - Src Port rule Enabled. 
		Bit11 - PPPoE Encapsulation rule Enabled."
	DEFVAL  { 0 }
	::= { worpQoSPIRTableEntry 3 }

worpQoSPIRIPToSLow  OBJECT-TYPE
	SYNTAX     Unsigned32 (0..255)
	MAX-ACCESS read-write
	STATUS     current
	DESCRIPTION 
		"This Parameter specifies the lower limit for the ToS (Types Of Service) classification."
	DEFVAL  { 0 }
	::= { worpQoSPIRTableEntry 4 }

worpQoSPIRIPToSHigh  OBJECT-TYPE
	SYNTAX     Unsigned32 (0..255)
	MAX-ACCESS read-write
	STATUS     current
	DESCRIPTION 
		"This Parameter specifies the higher limit for the ToS classification."
	DEFVAL  { 0 }
	::= { worpQoSPIRTableEntry 5 }

worpQoSPIRIPToSMask  OBJECT-TYPE
	SYNTAX     Unsigned32 (0..255)
	MAX-ACCESS read-write
	STATUS     current
	DESCRIPTION 
		"This Parameter specifies The ToS Mask which will be used to perform bitwise and 
		                 operation with incoming Packet's ToS values and it will be checked again Lower & 
		                 Hight limit the ToS Low, ToS High configuraiton."
	DEFVAL  { 0 }
	::= { worpQoSPIRTableEntry 6 }

worpQoSPIRIPProtocolIds  OBJECT-TYPE
	SYNTAX     DisplayString
	MAX-ACCESS read-write
	STATUS     current
	DESCRIPTION 
		"This Parameter specifies the Protocol Classification for the incoming packet."
	DEFVAL  { "0" }
	::= { worpQoSPIRTableEntry 7 }

worpQoSPIREtherPriorityLow  OBJECT-TYPE
	SYNTAX     Unsigned32 (0..7)
	MAX-ACCESS read-write
	STATUS     current
	DESCRIPTION 
		"This parameter specifies the lower limit for the 802.1p classificaiton for the incoming packet."
	DEFVAL  { 0 }
	::= { worpQoSPIRTableEntry 8 }

worpQoSPIREtherPriorityHigh  OBJECT-TYPE
	SYNTAX     Unsigned32 (0..7)
	MAX-ACCESS read-write
	STATUS     current
	DESCRIPTION 
		"This parameter specifies the Higher limit for the 802.1p classificaiton for the  
		                 incoming packet."
	DEFVAL  { 0 }
	::= { worpQoSPIRTableEntry 9 }

worpQoSPIRVlanId  OBJECT-TYPE
	SYNTAX     VlanId
	MAX-ACCESS read-write
	STATUS     current
	DESCRIPTION 
		"This parameter specifies the VLAN classification for the incoming packet."
	DEFVAL  { 1 }
	::= { worpQoSPIRTableEntry 10 }

worpQoSPIREtherType  OBJECT-TYPE
	SYNTAX     INTEGER {
		dix-snap (1),
		dsap (2)
	}
	MAX-ACCESS read-write
	STATUS     current
	DESCRIPTION 
		"This parameter specifies the Ether type classification for the incoming 
		                 ethernet frame."
	DEFVAL  { dix-snap }
	::= { worpQoSPIRTableEntry 11 }

worpQoSPIREtherValue  OBJECT-TYPE
	SYNTAX     OCTET STRING (SIZE(2))
	MAX-ACCESS read-write
	STATUS     current
	DESCRIPTION 
		"This parameter specifies the Ether Value classificaiton for the incoming 
		                 ethernet frame."
	::= { worpQoSPIRTableEntry 12 }

worpQoSPIRPPPoEEncapsulation  OBJECT-TYPE
	SYNTAX     INTEGER {
		enable (1),
		disable (2)
	}
	MAX-ACCESS read-write
	STATUS     current
	DESCRIPTION 
		"This parameter specifies the PPPoE (Point-to-point Protocol Over Ethernet) Encapsulation status for the incoming 
		                 ethernet frame."
	DEFVAL  { disable }
	::= { worpQoSPIRTableEntry 13 }

worpQoSPIRPPPoEProtocolId  OBJECT-TYPE
	SYNTAX     OCTET STRING (SIZE(2))
	MAX-ACCESS read-write
	STATUS     current
	DESCRIPTION 
		"This parameter specifies the protocol id inside the PPPoE Encapsulation 
		                 data for the incoming ethernet frame."
	::= { worpQoSPIRTableEntry 14 }

worpQoSPIRMapTableIndexVal  OBJECT-TYPE
	SYNTAX     Unsigned32 (1..255)
	MAX-ACCESS read-only
	STATUS     current
	DESCRIPTION 
		"This parameter specifies the index of the worpQoSPIRMapTable."
	::= { worpQoSPIRTableEntry 15 }

worpQoSPIRTableEntryStatus  OBJECT-TYPE
	SYNTAX     RowStatus
	MAX-ACCESS read-write
	STATUS     current
	DESCRIPTION 
		"This parameter is used to configure the worpQoSPIRTable status. 
		 It can be configured as 
		                 active(enable) -1, 
		                 notInService(disable) - 2, 
		                 createAndGo(create row) -4, 
		                 destroy(delete) - 6"
	DEFVAL  { active }
	::= { worpQoSPIRTableEntry 16 }

-- - WORP WoS SFC Class Group

worpQoSSFClassTable  OBJECT-TYPE
	SYNTAX SEQUENCE OF WorpQoSSFClassTableEntry
	MAX-ACCESS not-accessible
	STATUS     current
	DESCRIPTION 
		"This Table holds the Service Flow Classification (SFC) information for QoS feature."
	::= { worpQoS 6 }

worpQoSSFClassTableEntry  OBJECT-TYPE
	SYNTAX 	WorpQoSSFClassTableEntry
	MAX-ACCESS not-accessible
	STATUS     current
	DESCRIPTION 
		"This parameter represents the entry for the worpQoSSFClassTable."
	INDEX { worpQoSSFClassTableIndex }
	::= { worpQoSSFClassTable 1 }

WorpQoSSFClassTableEntry ::= SEQUENCE {
	worpQoSSFClassTableIndex
		Unsigned32,
	worpQoSSFClassName
		DisplayString,
	worpQoSSFClassSchedularType
		INTEGER,
	worpQoSSFClassDirection
		INTEGER,
	worpQoSSFClassStatus
		INTEGER,
	worpQoSSFClassMIR
		Unsigned32,
	worpQoSSFClassCIR
		Unsigned32,
	worpQoSSFClassMaxLatency
		Unsigned32,
	worpQoSSFClassTolerableJitter
		Unsigned32,
	worpQoSSFClassTrafficPriority
		Unsigned32,
	worpQoSSFClassNumOfMesgInBurst
		Unsigned32,
	worpQoSSFClassTableEntryStatus
		RowStatus,
	worpQoSSFClassMaxDemand
		INTEGER
}

worpQoSSFClassTableIndex  OBJECT-TYPE
	SYNTAX     Unsigned32 (1..32)
	MAX-ACCESS read-only
	STATUS     current
	DESCRIPTION 
		"This parameter specifies the index number of the entry in the worpQoSSFClassTable."
	::= { worpQoSSFClassTableEntry 1 }

worpQoSSFClassName  OBJECT-TYPE
	SYNTAX     DisplayString
	MAX-ACCESS read-write
	STATUS     current
	DESCRIPTION 
		"This parameter specifies the Service Flow Class Name."
	DEFVAL  { "default-sfc" }
	::= { worpQoSSFClassTableEntry 2 }

worpQoSSFClassSchedularType  OBJECT-TYPE
	SYNTAX     INTEGER {
		rtpS (1),
		be (2)
	}
	MAX-ACCESS read-write
	STATUS     current
	DESCRIPTION 
		"This parameter specifies the type of Scheduler to be used for this Service Flow.
		                  Select 1 for rtps - Real Time Polling Service
		                         2 for be   - Best Effort."
	DEFVAL  { be }
	::= { worpQoSSFClassTableEntry 3 }

worpQoSSFClassDirection  OBJECT-TYPE
	SYNTAX     INTEGER {
		uplink (1),
		downlink (2)
	}
	MAX-ACCESS read-write
	STATUS     current
	DESCRIPTION 
		"This parameter specifies the Direction of the Service Flow."
	DEFVAL  { downlink }
	::= { worpQoSSFClassTableEntry 4 }

worpQoSSFClassStatus  OBJECT-TYPE
	SYNTAX     INTEGER {
		active (1),
		in-active (2)
	}
	MAX-ACCESS read-only
	STATUS     current
	DESCRIPTION 
		"This parameter specifies the Status of the Service Flow."
	::= { worpQoSSFClassTableEntry 5 }

worpQoSSFClassMIR  OBJECT-TYPE
	SYNTAX     Unsigned32 (0..307200)
	MAX-ACCESS read-write
	STATUS     current
	DESCRIPTION 
		"This parameter specifies the Maximum Information Rate(MIR) for this Service Flow. 
		                  This value is represented in Kbps."
	::= { worpQoSSFClassTableEntry 6 }

worpQoSSFClassCIR  OBJECT-TYPE
	SYNTAX     Unsigned32 (0..307200)
	MAX-ACCESS read-write
	STATUS     current
	DESCRIPTION 
		"This parameter specifies the Comitted Information Rate(CIR) for this Service Flow.
		                  This value is represented in Kbps."
	DEFVAL  { 0 }
	::= { worpQoSSFClassTableEntry 7 }

worpQoSSFClassMaxLatency  OBJECT-TYPE
	SYNTAX     Unsigned32 (5..100)
	MAX-ACCESS read-write
	STATUS     current
	DESCRIPTION 
		"This parameter specifies the Latency for this Service Flow. This is represented in milliseconds."
	DEFVAL  { 10 }
	::= { worpQoSSFClassTableEntry 8 }

worpQoSSFClassTolerableJitter  OBJECT-TYPE
	SYNTAX     Unsigned32 (0..100)
	MAX-ACCESS read-write
	STATUS     current
	DESCRIPTION 
		"This parameter specifies the Jitter for this Service Flow. This is represented in milliseconds."
	DEFVAL  { 10 }
	::= { worpQoSSFClassTableEntry 9 }

worpQoSSFClassTrafficPriority  OBJECT-TYPE
	SYNTAX     Unsigned32 (0..7)
	MAX-ACCESS read-write
	STATUS     current
	DESCRIPTION 
		"This parameter specifies the priority of execution of the Service Flow inside a QoS Class."
	DEFVAL  { 0 }
	::= { worpQoSSFClassTableEntry 10 }

worpQoSSFClassNumOfMesgInBurst  OBJECT-TYPE
	SYNTAX     Unsigned32 (1..16)
	MAX-ACCESS read-write
	STATUS     current
	DESCRIPTION 
		"This parameter specifies the Number of maximum messages can be sent in a single burst."
	DEFVAL  { 4 }
	::= { worpQoSSFClassTableEntry 11 }

worpQoSSFClassTableEntryStatus  OBJECT-TYPE
	SYNTAX     RowStatus
	MAX-ACCESS read-write
	STATUS     current
	DESCRIPTION 
		"This parameter is used to configure the worpQoSSFClassTable status. 
		 It can be configured as 
		                 active(enable) -1, 
		                 notInService(disable) - 2, 
		                 createAndGo(create row) -4, 
		                 destroy(delete) - 6"
	DEFVAL  { active }
	::= { worpQoSSFClassTableEntry 12 }

worpQoSSFClassMaxDemand  OBJECT-TYPE
	SYNTAX     INTEGER {
		enable (1),
		disable (2)
	}
	MAX-ACCESS read-write
	STATUS     current
	DESCRIPTION 
		"This parameter is used to enable/disable max demand per SFC."
	DEFVAL  { disable }
	::= { worpQoSSFClassTableEntry 13 }

-- - WORP QoS Class Table Group

worpQoSClassTable  OBJECT-TYPE
	SYNTAX SEQUENCE OF WorpQoSClassTableEntry
	MAX-ACCESS not-accessible
	STATUS     current
	DESCRIPTION 
		"This Table holds the Class information for QoS feature."
	::= { worpQoS 7 }

worpQoSClassTableEntry  OBJECT-TYPE
	SYNTAX 	WorpQoSClassTableEntry
	MAX-ACCESS not-accessible
	STATUS     current
	DESCRIPTION 
		"This parameter represents the entry for the worpQoSClassTable."
	INDEX { worpQoSClassTableIndex, 
		worpQoSSFClassTableIndex, 
		worpQoSPIRTableIndex }
	::= { worpQoSClassTable 1 }

WorpQoSClassTableEntry ::= SEQUENCE {
	worpQoSClassTableIndex
		Unsigned32,
	worpQoSClassSFCTableIndex
		Unsigned32,
	worpQoSClassPIRTableIndex
		Unsigned32,
	worpQoSClassSFCValue
		Unsigned32,
	worpQoSClassPIRValue
		Unsigned32,
	worpQoSClassName
		DisplayString,
	worpQoSClassPriority
		Unsigned32,
	worpQoSClassTableEntryStatus
		RowStatus
}

worpQoSClassTableIndex  OBJECT-TYPE
	SYNTAX     Unsigned32 (1..8)
	MAX-ACCESS read-only
	STATUS     current
	DESCRIPTION 
		"This parameter specifies the QoS Class index."
	::= { worpQoSClassTableEntry 1 }

worpQoSClassSFCTableIndex  OBJECT-TYPE
	SYNTAX     Unsigned32 (1..8)
	MAX-ACCESS read-only
	STATUS     current
	DESCRIPTION 
		"This parameter specifies the SFC index within the QoS Class index."
	::= { worpQoSClassTableEntry 2 }

worpQoSClassPIRTableIndex  OBJECT-TYPE
	SYNTAX     Unsigned32 (1..8)
	MAX-ACCESS read-only
	STATUS     current
	DESCRIPTION 
		"This parameter specifies the PIR index within the QoS SFC index."
	::= { worpQoSClassTableEntry 3 }

worpQoSClassSFCValue  OBJECT-TYPE
	SYNTAX     Unsigned32 (1..32)
	MAX-ACCESS read-write
	STATUS     current
	DESCRIPTION 
		"This parameter specifies the reference index of the QoS SFC Table index."
	::= { worpQoSClassTableEntry 4 }

worpQoSClassPIRValue  OBJECT-TYPE
	SYNTAX     Unsigned32 (1..64)
	MAX-ACCESS read-write
	STATUS     current
	DESCRIPTION 
		"This parameter specifies the reference index of the QoS PIR Table index."
	::= { worpQoSClassTableEntry 5 }

worpQoSClassName  OBJECT-TYPE
	SYNTAX     DisplayString
	MAX-ACCESS read-write
	STATUS     current
	DESCRIPTION 
		"This parameter specifies the QoS Class Name."
	DEFVAL  { "default-class" }
	::= { worpQoSClassTableEntry 6 }

worpQoSClassPriority  OBJECT-TYPE
	SYNTAX     Unsigned32 (0..255)
	MAX-ACCESS read-write
	STATUS     current
	DESCRIPTION 
		"This parameter specifies the PIR Execution priority within a QoS Class"
	DEFVAL  { 0 }
	::= { worpQoSClassTableEntry 7 }

worpQoSClassTableEntryStatus  OBJECT-TYPE
	SYNTAX     RowStatus
	MAX-ACCESS read-write
	STATUS     current
	DESCRIPTION 
		"This parameter is used to configure the worpQoSClassTable status. 
		 It can be configured as 
		                 active(enable) -1, 
		                 notInService(disable) - 2, 
		                 createAndGo(create row) -4, 
		                 destroy(delete) - 6"
	DEFVAL  { active }
	::= { worpQoSClassTableEntry 8 }

-- WORP QoS SU Table Group

worpQoSSUTable  OBJECT-TYPE
	SYNTAX SEQUENCE OF WorpQoSSUTableEntry
	MAX-ACCESS not-accessible
	STATUS     current
	DESCRIPTION 
		"This Table holds the SU/End Point B entries for QoS feature."
	::= { worpQoS 8 }

worpQoSSUTableEntry  OBJECT-TYPE
	SYNTAX 	WorpQoSSUTableEntry
	MAX-ACCESS not-accessible
	STATUS     current
	DESCRIPTION 
		"This parameter represents the entry for the worpQoSSUTable."
	INDEX { worpQoSSUTableIndex }
	::= { worpQoSSUTable 1 }

WorpQoSSUTableEntry ::= SEQUENCE {
	worpQoSSUTableIndex
		Unsigned32,
	worpQoSSUMACAddress
		MacAddress,
	worpQoSSUQoSClassIndex
		Unsigned32,
	worpQoSSUComment
		DisplayString,
	worpQoSSUTableEntryStatus
		RowStatus
}

worpQoSSUTableIndex  OBJECT-TYPE
	SYNTAX     Unsigned32 (1..250)
	MAX-ACCESS read-only
	STATUS     current
	DESCRIPTION 
		"This parameter specifies the index number of the entry in the table "
	::= { worpQoSSUTableEntry 1 }

worpQoSSUMACAddress  OBJECT-TYPE
	SYNTAX     MacAddress
	MAX-ACCESS read-write
	STATUS     current
	DESCRIPTION 
		"This parameter specifies the wireless MAC Address of the SU or End Point B"
	::= { worpQoSSUTableEntry 2 }

worpQoSSUQoSClassIndex  OBJECT-TYPE
	SYNTAX     Unsigned32 (1..8)
	MAX-ACCESS read-write
	STATUS     current
	DESCRIPTION 
		"This parameter specifies the reference index of the QoS Class Table index."
	::= { worpQoSSUTableEntry 3 }

worpQoSSUComment  OBJECT-TYPE
	SYNTAX     DisplayString
	MAX-ACCESS read-write
	STATUS     current
	DESCRIPTION 
		"This parameter specifies the comment for this entry."
	DEFVAL  { "default-su" }
	::= { worpQoSSUTableEntry 4 }

worpQoSSUTableEntryStatus  OBJECT-TYPE
	SYNTAX     RowStatus
	MAX-ACCESS read-write
	STATUS     current
	DESCRIPTION 
		"This parameter is used to configure the worpQoSSUTable status. 
		 It can be configured as 
		                 active(enable) -1, 
		                 notInService(disable) - 2, 
		                 createAndGo(create row) -4, 
		                 destroy(delete) - 6"
	DEFVAL  { active }
	::= { worpQoSSUTableEntry 5 }

-- worp QOS Default Class

worpQoSDefaultClass  OBJECT-TYPE
	SYNTAX     Unsigned32 (1..8)
	MAX-ACCESS read-write
	STATUS     current
	DESCRIPTION 
		"This parameter specifies the QoS Class need to be used by the SU/End Point B connected 
		                 to BSU/End Point A but not listed in the worpQoSSUTable."
	::= { worpQoS 9 }

worpQoSL2BroadcastClass  OBJECT-TYPE
	SYNTAX     Unsigned32 (0..8)
	MAX-ACCESS read-write
	STATUS     current
	DESCRIPTION 
		"This parameter specifies the QoS Class need to be used for the Layer 2 Broadcast 
		                 traffic on the Downlink direction."
	::= { worpQoS 10 }

-- ======================================================================================
-- Net IP Subgroup Objects : netIp
-- ======================================================================================
-- Net IP Config Table

netIpCfgTable  OBJECT-TYPE
	SYNTAX SEQUENCE OF NetIpCfgTableEntry
	MAX-ACCESS not-accessible
	STATUS     current
	DESCRIPTION 
		"This table is used to configure the network IP parameters."
	::= { netIp 1 }

netIpCfgTableEntry  OBJECT-TYPE
	SYNTAX 	NetIpCfgTableEntry
	MAX-ACCESS not-accessible
	STATUS     current
	DESCRIPTION 
		"This table represents the entry for the network IP configuration table"
	INDEX { netIpCfgTableIndex }
	::= { netIpCfgTable 1 }

NetIpCfgTableEntry ::= SEQUENCE {
	netIpCfgTableIndex
		Unsigned32,
	netIpCfgIPAddress
		IpAddress,
	netIpCfgSubnetMask
		IpAddress,
	netIpCfgDefaultRouterIPAddress
		IpAddress,
	netIpCfgAddressType
		INTEGER,
	netIpCfgInetAddress
		InetAddress,
	netIpCfgInetAddressType
		INTEGER,
	netIpCfgLinklocalInetAddress
		InetAddress,
	netIpCfgIPMode
		INTEGER,
	netIpCfgInetAddressPrefixLength
		Integer32
}

netIpCfgTableIndex  OBJECT-TYPE
	SYNTAX     Unsigned32
	MAX-ACCESS read-only
	STATUS     current
	DESCRIPTION 
		"This parameter represents the index for the network IP configuration table 
		                  and interface number."
	::= { netIpCfgTableEntry 1 }

netIpCfgIPAddress  OBJECT-TYPE
	SYNTAX     IpAddress
	MAX-ACCESS read-write
	STATUS     current
	DESCRIPTION 
		"This parameter is used to configure the IP Address for the ethernet interface."
	DEFVAL  { 'a9fe8084'H }
	::= { netIpCfgTableEntry 2 }

netIpCfgSubnetMask  OBJECT-TYPE
	SYNTAX     IpAddress
	MAX-ACCESS read-write
	STATUS     current
	DESCRIPTION 
		"This parameter is used to configure the subnet mask for the ethernet interface."
	DEFVAL  { 'ffff0000'H }
	::= { netIpCfgTableEntry 3 }

netIpCfgDefaultRouterIPAddress  OBJECT-TYPE
	SYNTAX     IpAddress
	MAX-ACCESS read-write
	STATUS     deprecated
	DESCRIPTION 
		"This parameter is used to set the IP address of the gateway or router of the device.
		                 This parameter is deprecated and please use the object
		                                  netCfgAllIntfDefaultRouterIpAddr to set the gateway IP address."
	::= { netIpCfgTableEntry 4 }

netIpCfgAddressType  OBJECT-TYPE
	SYNTAX     INTEGER {
		static (1),
		dynamic (2)
	}
	MAX-ACCESS read-write
	STATUS     current
	DESCRIPTION 
		" This parameter is used to specify whether the device network paramenters
		  are to be configured through a dhcp client or to be assigned statically.
		  If the value is set to 1, then the device is configured as static. 
		  If the value is set to 2, then the device is set to dynamic."
	DEFVAL  { static }
	::= { netIpCfgTableEntry 5 }

netIpCfgInetAddress  OBJECT-TYPE
	SYNTAX     InetAddress
	MAX-ACCESS read-write
	STATUS     current
	DESCRIPTION 
		"This parameter is used to configure the Inet Address for the ethernet interface."
	::= { netIpCfgTableEntry 6 }

netIpCfgInetAddressType  OBJECT-TYPE
	SYNTAX     INTEGER {
		static (1),
		dynamic (2),
		auto (3)
	}
	MAX-ACCESS read-write
	STATUS     current
	DESCRIPTION 
		" This parameter is used to acquire IPv6 address by auto/static/dynamic."
	DEFVAL  { auto }
	::= { netIpCfgTableEntry 7 }

netIpCfgLinklocalInetAddress  OBJECT-TYPE
	SYNTAX     InetAddress
	MAX-ACCESS read-only
	STATUS     current
	DESCRIPTION 
		"This parameter is used to configure the Linklocal Inet Address for the ethernet interface."
	::= { netIpCfgTableEntry 8 }

netIpCfgIPMode  OBJECT-TYPE
	SYNTAX     INTEGER {
		ipv4Only (1),
		ipv4Andipv6 (2)
	}
	MAX-ACCESS read-write
	STATUS     current
	DESCRIPTION 
		" This parameter is used to enable/disable the ipv6 feature."
	DEFVAL  { ipv4Only }
	::= { netIpCfgTableEntry 9 }

netIpCfgInetAddressPrefixLength  OBJECT-TYPE
	SYNTAX     Integer32 (0..128)
	MAX-ACCESS read-write
	STATUS     current
	DESCRIPTION 
		" This parameter is used for Inet Address prefix length."
	::= { netIpCfgTableEntry 10 }

-- Wireless Net IP Config Table

netIpWirelessCfgTable  OBJECT-TYPE
	SYNTAX SEQUENCE OF NetIpWirelessCfgTableEntry
	MAX-ACCESS not-accessible
	STATUS     current
	DESCRIPTION 
		"This table is used to configure the wireless network IP parameters in
		                 routing mode."
	::= { netIp 2 }

netIpWirelessCfgTableEntry  OBJECT-TYPE
	SYNTAX 	NetIpWirelessCfgTableEntry
	MAX-ACCESS not-accessible
	STATUS     current
	DESCRIPTION 
		"This table represents the entry for the network IP configuration table"
	INDEX { netIpWirelessCfgTableIndex }
	::= { netIpWirelessCfgTable 1 }

NetIpWirelessCfgTableEntry ::= SEQUENCE {
	netIpWirelessCfgTableIndex
		Unsigned32,
	netIpWirelessCfgIPAddress
		IpAddress,
	netIpWirelessCfgSubnetMask
		IpAddress,
	netIpWirelessCfgAddrType
		INTEGER,
	netIpWirelessCfgPPPoESecInetAddress
		InetAddress,
	netIpWirelessCfgPPPoESecMask
		IpAddress
}

netIpWirelessCfgTableIndex  OBJECT-TYPE
	SYNTAX     Unsigned32
	MAX-ACCESS read-only
	STATUS     current
	DESCRIPTION 
		"This parameter is user defined  index or interface number in the 
		 network IP wireless configuration table."
	::= { netIpWirelessCfgTableEntry 1 }

netIpWirelessCfgIPAddress  OBJECT-TYPE
	SYNTAX     IpAddress
	MAX-ACCESS read-write
	STATUS     current
	DESCRIPTION 
		"This parameter is used to configure the IP Address for the wireless interface."
	::= { netIpWirelessCfgTableEntry 2 }

netIpWirelessCfgSubnetMask  OBJECT-TYPE
	SYNTAX     IpAddress
	MAX-ACCESS read-write
	STATUS     current
	DESCRIPTION 
		"This parameter is used to configure the subnet mask for the wireless interface."
	::= { netIpWirelessCfgTableEntry 3 }

netIpWirelessCfgAddrType  OBJECT-TYPE
	SYNTAX     INTEGER {
		static (1),
		pppoe-ipcp (2)
	}
	MAX-ACCESS read-write
	STATUS     current
	DESCRIPTION 
		"This parameter is used to configure wireless address type."
	::= { netIpWirelessCfgTableEntry 4 }

netIpWirelessCfgPPPoESecInetAddress  OBJECT-TYPE
	SYNTAX     InetAddress
	MAX-ACCESS read-write
	STATUS     current
	DESCRIPTION 
		"This parameter is used to configure PPPoE secondary Inet address."
	::= { netIpWirelessCfgTableEntry 5 }

netIpWirelessCfgPPPoESecMask  OBJECT-TYPE
	SYNTAX     IpAddress
	MAX-ACCESS read-write
	STATUS     current
	DESCRIPTION 
		"This parameter is used to configure PPPoE secondary mask."
	::= { netIpWirelessCfgTableEntry 6 }

-- Network Static Route Table

netIpStaticRouteTable  OBJECT-TYPE
	SYNTAX SEQUENCE OF NetIpStaticRouteTableEntry
	MAX-ACCESS not-accessible
	STATUS     current
	DESCRIPTION 
		"This table is used to configure the static routes in routing mode."
	::= { netIp 3 }

netIpStaticRouteTableEntry  OBJECT-TYPE
	SYNTAX 	NetIpStaticRouteTableEntry
	MAX-ACCESS not-accessible
	STATUS     current
	DESCRIPTION 
		"This parameter represents the entry status for the netIpStaticRouteTable
		                 and this table holds upto 256 entries."
	INDEX { netIpStaticRouteTableIndex }
	::= { netIpStaticRouteTable 1 }

NetIpStaticRouteTableEntry ::= SEQUENCE {
	netIpStaticRouteTableIndex
		Unsigned32,
	netIpStaticRouteDestAddr
		IpAddress,
	netIpStaticRouteMask
		IpAddress,
	netIpStaticRouteNextHop
		IpAddress,
	netIpStaticRouteMetric
		Unsigned32,
	netIpStaticRouteTableEntryStatus
		RowStatus
}

netIpStaticRouteTableIndex  OBJECT-TYPE
	SYNTAX     Unsigned32 (0..256)
	MAX-ACCESS read-only
	STATUS     current
	DESCRIPTION 
		"This parameter represents the index of the netIpStaticRouteTable."
	::= { netIpStaticRouteTableEntry 1 }

netIpStaticRouteDestAddr  OBJECT-TYPE
	SYNTAX     IpAddress
	MAX-ACCESS read-write
	STATUS     current
	DESCRIPTION 
		"This parameter is used to enter the destination IP address for which
		                 the static route is to be made."
	::= { netIpStaticRouteTableEntry 2 }

netIpStaticRouteMask  OBJECT-TYPE
	SYNTAX     IpAddress
	MAX-ACCESS read-write
	STATUS     current
	DESCRIPTION 
		"This parameter is used to enter the mask for the destination address."
	::= { netIpStaticRouteTableEntry 3 }

netIpStaticRouteNextHop  OBJECT-TYPE
	SYNTAX     IpAddress
	MAX-ACCESS read-write
	STATUS     current
	DESCRIPTION 
		"This parameter represents the next reachable hop using which route is made
		                 to the destination IP address."
	::= { netIpStaticRouteTableEntry 4 }

netIpStaticRouteMetric  OBJECT-TYPE
	SYNTAX     Unsigned32 (0..16)
	MAX-ACCESS read-write
	STATUS     current
	DESCRIPTION 
		"This parameter represents the Metric, i.e.,the 'distance' to the target 
		                 (usually counted in hops)."
	::= { netIpStaticRouteTableEntry 5 }

netIpStaticRouteTableEntryStatus  OBJECT-TYPE
	SYNTAX     RowStatus
	MAX-ACCESS read-write
	STATUS     current
	DESCRIPTION 
		"This parameter is used to configure the netIpStaticRouteTable status. 
		 It can be configured as 
		                 active(enable) -1, 
		                 notInService(disable) - 2, 
		                 createAndGo(create row) -4, 
		                 destroy(delete) - 6"
	::= { netIpStaticRouteTableEntry 6 }

-- Network Address Table

netIpAddressTable  OBJECT-TYPE
	SYNTAX SEQUENCE OF NetIpAddressEntry
	MAX-ACCESS not-accessible
	STATUS     current
	DESCRIPTION 
		"This table is used to configure the IP parameters."
	::= { netIp 4 }

netIpAddressEntry  OBJECT-TYPE
	SYNTAX 	NetIpAddressEntry
	MAX-ACCESS not-accessible
	STATUS     current
	DESCRIPTION 
		""
	INDEX { netIpAddressInterfaceType, 
		netIpAddressInterfaceIndex, 
		netIpAddressSubIndex }
	::= { netIpAddressTable 1 }

NetIpAddressEntry ::= SEQUENCE {
	netIpAddressInterfaceType
		Unsigned32,
	netIpAddressInterfaceIndex
		Unsigned32,
	netIpAddressSubIndex
		Unsigned32,
	netIpAddressInetAddress
		InetAddress,
	netIpAddressInetAddrType
		INTEGER,
	netIpAddressInterfaceName
		DisplayString,
	netIpAddressEntryStatus
		RowStatus
}

netIpAddressInterfaceType  OBJECT-TYPE
	SYNTAX     Unsigned32
	MAX-ACCESS read-only
	STATUS     current
	DESCRIPTION 
		"This parameter represents the interface type.
		 ethernet 1
		 wireless 2
		 PPPoE    3
		 IPinIP   4
		 LoopBack 5."
	::= { netIpAddressEntry 1 }

netIpAddressInterfaceIndex  OBJECT-TYPE
	SYNTAX     Unsigned32
	MAX-ACCESS read-only
	STATUS     current
	DESCRIPTION 
		"This parameter represents the interface index."
	::= { netIpAddressEntry 2 }

netIpAddressSubIndex  OBJECT-TYPE
	SYNTAX     Unsigned32
	MAX-ACCESS read-only
	STATUS     current
	DESCRIPTION 
		"This parameter represents the sub index."
	::= { netIpAddressEntry 3 }

netIpAddressInetAddress  OBJECT-TYPE
	SYNTAX     InetAddress
	MAX-ACCESS read-write
	STATUS     current
	DESCRIPTION 
		"This parameter represents the inet address."
	::= { netIpAddressEntry 4 }

netIpAddressInetAddrType  OBJECT-TYPE
	SYNTAX     INTEGER {
		ipv4 (1),
		ipv6 (2)
	}
	MAX-ACCESS read-write
	STATUS     current
	DESCRIPTION 
		"This parameter represents the inet address type."
	::= { netIpAddressEntry 5 }

netIpAddressInterfaceName  OBJECT-TYPE
	SYNTAX     DisplayString (SIZE(1..32))
	MAX-ACCESS read-write
	STATUS     current
	DESCRIPTION 
		"This parameter represents the interface name."
	::= { netIpAddressEntry 6 }

netIpAddressEntryStatus  OBJECT-TYPE
	SYNTAX     RowStatus
	MAX-ACCESS read-write
	STATUS     current
	DESCRIPTION 
		"This parameter is used to configure the netIpAddressTable status. 
		 It can be configured as 
		                 active(enable) -1, 
		                 notInService(disable) - 2, 
		                 createAndGo(create row) -4, 
		                 destroy(delete) - 6"
	::= { netIpAddressEntry 7 }

-- ======================================================================================
-- Network Configuration Subgroup Objects : netCfg
-- ======================================================================================
-- Clear Interface Stats 

netCfgClearIntfStats  OBJECT-TYPE
	SYNTAX     INTEGER {
		none (1),
		ethernetIntf1 (2),
		ethernetIntf2 (3),
		bridgeStats (4),
		arpTable (5),
		wirelessIntf1 (6),
		wirelessIntf2 (7),
		worpIntf1 (8),
		worpIntf2 (9),
		learnTable (10),
		pppoeIfStats (11),
		pppoeConnStats (12)
	}
	MAX-ACCESS read-write
	STATUS     current
	DESCRIPTION 
		"This parameter is used to clear the wired/wireless interface statistics."
	DEFVAL  { none }
	::= { netCfg 1 }

-- Default Router Ip Address

netCfgAllIntfDefaultRouterAddr  OBJECT-TYPE
	SYNTAX     IpAddress
	MAX-ACCESS read-write
	STATUS     current
	DESCRIPTION 
		"Default Router Address that applies to all interfaces."
	::= { netCfg 2 }

-- Number of supported interfaces

netCfgSupportedInterfaces  OBJECT-TYPE
	SYNTAX     DisplayString (SIZE(0..32))
	MAX-ACCESS read-only
	STATUS     current
	DESCRIPTION 
		"This parameter shows the names of supported interfaces depending on the
		                 network mode."
	::= { netCfg 3 }

-- Static Route Status

netCfgStaticRouteStatus  OBJECT-TYPE
	SYNTAX     INTEGER {
		enable (1),
		disable (2)
	}
	MAX-ACCESS read-write
	STATUS     current
	DESCRIPTION 
		"This parameter is used to enable/disable the static routes option."
	DEFVAL  { disable }
	::= { netCfg 4 }

-- Wireless Inactivity Timer

wirelessInActivityTimer  OBJECT-TYPE
	SYNTAX     Unsigned32 (0..600)
	MAX-ACCESS read-write
	STATUS     deprecated
	DESCRIPTION 
		"This parameter is used to monitor the wireless interface for every specified number of minutes.
		                 The value 0 disables monitoring."
	::= { netCfg 5 }

-- Ethernet Inactivity Timer

ethernetInActivityTimer  OBJECT-TYPE
	SYNTAX     Unsigned32 (0..600)
	MAX-ACCESS read-write
	STATUS     current
	DESCRIPTION 
		"This parameter is used to monitor the ethernet interface for every specified number of minutes.
		                 The value 0 disables monitoring."
	::= { netCfg 6 }

-- Primary DNS IP Address

netCfgPrimaryDNSIpAddress  OBJECT-TYPE
	SYNTAX     IpAddress
	MAX-ACCESS read-write
	STATUS     deprecated
	DESCRIPTION 
		"This parameter is to configure the Primary DNS IP Address to be used by this product.
		         This is now deprecated. Instead use netCfgPrimaryDNSInetAddress."
	::= { netCfg 7 }

-- Secondary DNS IP Address

netCfgSecondaryDNSIpAddress  OBJECT-TYPE
	SYNTAX     IpAddress
	MAX-ACCESS read-write
	STATUS     deprecated
	DESCRIPTION 
		"This parameter is to configure the Secondary DNS IP Address to be used by this product.
		         This is now deprecated. Instead use netCfgSecondaryDNSInetAddress."
	::= { netCfg 8 }

-- Wireless Inactivity Timer in Seconds

wirelessInActivityTimerInSecs  OBJECT-TYPE
	SYNTAX     Unsigned32 (0..3600)
	MAX-ACCESS read-write
	STATUS     current
	DESCRIPTION 
		"This parameter is used to monitor the wireless interface for every specified number of seconds.
		                 The value 0 disables monitoring. It can be configured from 5 to 600 seconds."
	::= { netCfg 9 }

netCfgClearIpTunnelStats  OBJECT-TYPE
	SYNTAX     Unsigned32
	MAX-ACCESS read-write
	STATUS     current
	DESCRIPTION 
		""
	::= { netCfg 10 }

netCfgDNSProxyStatus  OBJECT-TYPE
	SYNTAX     INTEGER {
		enable (1),
		disable (2)
	}
	MAX-ACCESS read-write
	STATUS     current
	DESCRIPTION 
		"This parameter is used to enable/disable the DNS Proxy Status."
	DEFVAL  { enable }
	::= { netCfg 11 }

-- Default Gateway Inet Address

netCfgDefaultGatewayInetAddress  OBJECT-TYPE
	SYNTAX     InetAddress
	MAX-ACCESS read-write
	STATUS     current
	DESCRIPTION 
		"Default Gateway Inet Address that applies to all interfaces."
	::= { netCfg 12 }

-- Primary DNS Inet Address

netCfgPrimaryDNSInetAddress  OBJECT-TYPE
	SYNTAX     InetAddress
	MAX-ACCESS read-write
	STATUS     current
	DESCRIPTION 
		"This parameter is to configure the Primary DNS Inet Address to be used by this product."
	::= { netCfg 13 }

-- Secondary DNS Inet Address

netCfgSecondaryDNSInetAddress  OBJECT-TYPE
	SYNTAX     InetAddress
	MAX-ACCESS read-write
	STATUS     current
	DESCRIPTION 
		"This parameter is to configure the Secondary DNS Inet Address to be used by this product."
	::= { netCfg 14 }
-- Controller IP Address.

netCfgControllerIPAddress  OBJECT-TYPE
	SYNTAX     InetAddress
	MAX-ACCESS read-write
	STATUS     current
	DESCRIPTION 
		"This parameter is used to configure the Controller IP Address."
	::= { netCfg 15 }

-- Active Controller IP Address.

netCfgActiveControllerIPAddress  OBJECT-TYPE
	SYNTAX     InetAddress
	MAX-ACCESS read-only
	STATUS     current
	DESCRIPTION 
		"This parameter is to Display the Active Controller IP Address."
	::= { netCfg 16 }

-- ======================================================================================
-- Network Address Translation Subgroup Objects : nat
-- ======================================================================================
-- NAT status

natStatus  OBJECT-TYPE
	SYNTAX     INTEGER {
		enable (1),
		disable (2)
	}
	MAX-ACCESS read-write
	STATUS     current
	DESCRIPTION 
		"This parameter is used to configure the NAT(Network Address Translation)
		                 status."
	::= { nat 1 }

-- NAT Port Binding Status

natPortBindingStatus  OBJECT-TYPE
	SYNTAX     INTEGER {
		enable (1),
		disable (2)
	}
	MAX-ACCESS read-write
	STATUS     current
	DESCRIPTION 
		"This parameter is used to enable or disable static bind entries 
		    on the NAT device. "
	::= { nat 2 }

-- NAT Static Port Binding Table

natStaticPortBindTable  OBJECT-TYPE
	SYNTAX SEQUENCE OF NatStaticPortBindTableEntry
	MAX-ACCESS not-accessible
	STATUS     current
	DESCRIPTION 
		"This table is used to configure NAT Port bind specific 
		information."
	::= { nat 3 }

natStaticPortBindTableEntry  OBJECT-TYPE
	SYNTAX 	NatStaticPortBindTableEntry
	MAX-ACCESS not-accessible
	STATUS     current
	DESCRIPTION 
		"This parameter represents an entry in the NAT Static Port Bind 
		Table."
	INDEX { natStaticPortBindTableIndex }
	::= { natStaticPortBindTable 1 }

NatStaticPortBindTableEntry ::= SEQUENCE {
	natStaticPortBindTableIndex
		Unsigned32,
	natStaticPortBindLocalAddr
		IpAddress,
	natStaticPortBindPortType
		INTEGER,
	natStaticPortBindStartPortNum
		Unsigned32,
	natStaticPortBindEndPortNum
		Unsigned32,
	natStaticPortBindTableEntryStatus
		RowStatus
}

natStaticPortBindTableIndex  OBJECT-TYPE
	SYNTAX     Unsigned32 (0..100)
	MAX-ACCESS read-only
	STATUS     current
	DESCRIPTION 
		"This parameter is used as  the index for the NAT static Port 
		bind table."
	::= { natStaticPortBindTableEntry 1 }

natStaticPortBindLocalAddr  OBJECT-TYPE
	SYNTAX     IpAddress
	MAX-ACCESS read-write
	STATUS     current
	DESCRIPTION 
		"This parameter represents the local IP address for this NAT Static
		  Port bind Table entry."
	::= { natStaticPortBindTableEntry 2 }

natStaticPortBindPortType  OBJECT-TYPE
	SYNTAX     INTEGER {
		tcp (1),
		udp (2),
		both (3)
	}
	MAX-ACCESS read-write
	STATUS     current
	DESCRIPTION 
		"This parameter represents the port type for this NAT Static
		    Port bind Table entry."
	::= { natStaticPortBindTableEntry 3 }

natStaticPortBindStartPortNum  OBJECT-TYPE
	SYNTAX     Unsigned32 (0..65535)
	MAX-ACCESS read-write
	STATUS     current
	DESCRIPTION 
		"This parameter represents the start port number for this NAT Static
		    Port bind Table entry."
	::= { natStaticPortBindTableEntry 4 }

natStaticPortBindEndPortNum  OBJECT-TYPE
	SYNTAX     Unsigned32 (0..65535)
	MAX-ACCESS read-write
	STATUS     current
	DESCRIPTION 
		"This parameter represents the end port number for this NAT Static
		    Port bind Table entry."
	::= { natStaticPortBindTableEntry 5 }

natStaticPortBindTableEntryStatus  OBJECT-TYPE
	SYNTAX     RowStatus
	MAX-ACCESS read-write
	STATUS     current
	DESCRIPTION 
		"This parameter is used to configure the natStaticPortBindTable status. 
		 It can be configured as 
		                 active(enable) -1, 
		                 notInService(disable) - 2, 
		                 createAndGo(create row) -4, 
		                 destroy(delete) - 6"
	::= { natStaticPortBindTableEntry 6 }

-- Nat Dynamic Start Port

natDynamicStartPort  OBJECT-TYPE
	SYNTAX     Integer32 (1..65535)
	MAX-ACCESS read-write
	STATUS     current
	DESCRIPTION 
		"This parameter represents the Dynamic Start Port Number"
	::= { nat 4 }

-- Nat Dynamic End Port

natDynamicEndPort  OBJECT-TYPE
	SYNTAX     Integer32 (1..65535)
	MAX-ACCESS read-write
	STATUS     current
	DESCRIPTION 
		"This parameter represents the Dynamic End Port Number"
	::= { nat 5 }

-- ======================================================================================
-- Routing Information Protocol Subgroup Objects : rip 
-- ======================================================================================
-- RIP Config Status

ripConfigStatus  OBJECT-TYPE
	SYNTAX     INTEGER {
		enable (1),
		disable (2)
	}
	MAX-ACCESS read-write
	STATUS     current
	DESCRIPTION 
		"This parameter is used to configure the RIP configuration status."
	DEFVAL  { disable }
	::= { rip 1 }

-- RIP Config Table

ripConfigTable  OBJECT-TYPE
	SYNTAX SEQUENCE OF RipConfigTableEntry
	MAX-ACCESS not-accessible
	STATUS     current
	DESCRIPTION 
		"This table is used to configure the RIP configuration information."
	::= { rip 2 }

ripConfigTableEntry  OBJECT-TYPE
	SYNTAX 	RipConfigTableEntry
	MAX-ACCESS not-accessible
	STATUS     current
	DESCRIPTION 
		"This parameter represents the entry for the ripConfigTable."
	INDEX { ripConfigTableIndex }
	::= { ripConfigTable 1 }

RipConfigTableEntry ::= SEQUENCE {
	ripConfigTableIndex
		Unsigned32,
	ripInterfaceName
		DisplayString,
	ripInterfaceStatus
		INTEGER,
	ripInterfaceAuthType
		INTEGER,
	ripInterfaceAuthKey
		DisplayString,
	ripInterfaceVersionNum
		INTEGER,
	ripReceiveOnly
		INTEGER
}

ripConfigTableIndex  OBJECT-TYPE
	SYNTAX     Unsigned32
	MAX-ACCESS read-only
	STATUS     current
	DESCRIPTION 
		"This parameter represents the index for ripConfigTable."
	::= { ripConfigTableEntry 1 }

ripInterfaceName  OBJECT-TYPE
	SYNTAX     DisplayString
	MAX-ACCESS read-only
	STATUS     current
	DESCRIPTION 
		"This parameter shows the available interfaces for which the rip can
		                 be configured."
	::= { ripConfigTableEntry 2 }

ripInterfaceStatus  OBJECT-TYPE
	SYNTAX     INTEGER {
		enable (1),
		disable (2)
	}
	MAX-ACCESS read-write
	STATUS     current
	DESCRIPTION 
		"This parameter is used to enable/disable the rip for the particular 
		                 interface."
	::= { ripConfigTableEntry 3 }

ripInterfaceAuthType  OBJECT-TYPE
	SYNTAX     INTEGER {
		simple (1),
		md5 (2),
		none (3)
	}
	MAX-ACCESS read-write
	STATUS     current
	DESCRIPTION 
		"This parameter represents the authentication type used for rip configuration."
	::= { ripConfigTableEntry 4 }

ripInterfaceAuthKey  OBJECT-TYPE
	SYNTAX     DisplayString (SIZE(0..32))
	MAX-ACCESS read-write
	STATUS     current
	DESCRIPTION 
		"This parameter is used to configure the authentication key for the authentication
		                 type."
	::= { ripConfigTableEntry 5 }

ripInterfaceVersionNum  OBJECT-TYPE
	SYNTAX     INTEGER {
		v1 (1),
		v2 (2),
		both (3)
	}
	MAX-ACCESS read-write
	STATUS     current
	DESCRIPTION 
		"This parameters allows to configure the rip version verion."
	DEFVAL  { v2 }
	::= { ripConfigTableEntry 6 }

ripReceiveOnly  OBJECT-TYPE
	SYNTAX     INTEGER {
		yes (1),
		no (2)
	}
	MAX-ACCESS read-write
	STATUS     current
	DESCRIPTION 
		"This parameter allows to configure the interface to receive only RIP
		                 version 1 and/or RIP verison 2 packets."
	::= { ripConfigTableEntry 7 }

-- ======================================================================================
-- Tunneling Subgroup Objects : tunneling
-- ======================================================================================
-- Tunneling Configuration Subgroup

tunnelingStatus  OBJECT-TYPE
	SYNTAX     INTEGER {
		enable (1),
		disable (2)
	}
	MAX-ACCESS read-write
	STATUS     current
	DESCRIPTION 
		""
	::= { tunneling 1 }

tunnelConfigTable  OBJECT-TYPE
	SYNTAX SEQUENCE OF TunnelConfigTableEntry
	MAX-ACCESS not-accessible
	STATUS     current
	DESCRIPTION 
		"TBD."
	::= { tunneling 2 }

tunnelConfigTableEntry  OBJECT-TYPE
	SYNTAX 	TunnelConfigTableEntry
	MAX-ACCESS not-accessible
	STATUS     current
	DESCRIPTION 
		"TBD"
	INDEX { tunnelConfigTableIndex }
	::= { tunnelConfigTable 1 }

TunnelConfigTableEntry ::= SEQUENCE {
	tunnelConfigTableIndex
		Unsigned32,
	tunnelConfigName
		DisplayString,
	tunnelConfigEncapMethod
		INTEGER,
	tunnelConfigVirtualIPAddress
		IpAddress,
	tunnelConfigLocalIPAddress
		IpAddress,
	tunnelConfigRemoteIPAddress
		IpAddress,
	tunnelConfigTTL
		Unsigned32,
	tunnelConfigTableEntryStatus
		RowStatus
}

tunnelConfigTableIndex  OBJECT-TYPE
	SYNTAX     Unsigned32
	MAX-ACCESS read-only
	STATUS     current
	DESCRIPTION 
		"TBD."
	::= { tunnelConfigTableEntry 1 }

tunnelConfigName  OBJECT-TYPE
	SYNTAX     DisplayString
	MAX-ACCESS read-write
	STATUS     current
	DESCRIPTION 
		"TBD."
	::= { tunnelConfigTableEntry 2 }

tunnelConfigEncapMethod  OBJECT-TYPE
	SYNTAX     INTEGER {
		ipip (1),
		gre (2)
	}
	MAX-ACCESS read-write
	STATUS     current
	DESCRIPTION 
		"TBD."
	::= { tunnelConfigTableEntry 3 }

tunnelConfigVirtualIPAddress  OBJECT-TYPE
	SYNTAX     IpAddress
	MAX-ACCESS read-write
	STATUS     current
	DESCRIPTION 
		"TBD."
	::= { tunnelConfigTableEntry 4 }

tunnelConfigLocalIPAddress  OBJECT-TYPE
	SYNTAX     IpAddress
	MAX-ACCESS read-write
	STATUS     current
	DESCRIPTION 
		"TBD."
	::= { tunnelConfigTableEntry 5 }

tunnelConfigRemoteIPAddress  OBJECT-TYPE
	SYNTAX     IpAddress
	MAX-ACCESS read-write
	STATUS     current
	DESCRIPTION 
		"TBD."
	::= { tunnelConfigTableEntry 6 }

tunnelConfigTTL  OBJECT-TYPE
	SYNTAX     Unsigned32
	MAX-ACCESS read-write
	STATUS     current
	DESCRIPTION 
		"TBD."
	::= { tunnelConfigTableEntry 7 }

tunnelConfigTableEntryStatus  OBJECT-TYPE
	SYNTAX     RowStatus
	MAX-ACCESS read-write
	STATUS     current
	DESCRIPTION 
		"TBD."
	::= { tunnelConfigTableEntry 8 }

-- ======================================================================================
-- Point-to-point over ethernet Protocol Subgroup Objects : pppoe
-- ======================================================================================
-- PPPOE Status

pppoeStatus  OBJECT-TYPE
	SYNTAX     INTEGER {
		enable (1),
		disable (2)
	}
	MAX-ACCESS read-write
	STATUS     current
	DESCRIPTION 
		"TBD"
	DEFVAL  { disable }
	::= { pppoe 1 }

-- PPPOE Authentication Protocol

pppoeAuthProtocol  OBJECT-TYPE
	SYNTAX     INTEGER {
		none (1),
		pap (2),
		chap (3),
		msChapv2 (4),
		eapMd5 (5)
	}
	MAX-ACCESS read-write
	STATUS     current
	DESCRIPTION 
		"TBD"
	::= { pppoe 2 }

-- PPPOE LCP Echo Interval

pppoeLcpEchoInterval  OBJECT-TYPE
	SYNTAX     Unsigned32 (5..300)
	MAX-ACCESS read-write
	STATUS     current
	DESCRIPTION 
		"TBD"
	::= { pppoe 3 }

-- PPPOE LCP Echo Failure

pppoeLcpEchoFailure  OBJECT-TYPE
	SYNTAX     Unsigned32 (1..25)
	MAX-ACCESS read-write
	STATUS     current
	DESCRIPTION 
		"TBD"
	::= { pppoe 4 }

-- PPPOE Preferred Service Name

pppoePreferredServiceName  OBJECT-TYPE
	SYNTAX     DisplayString (SIZE(0..32))
	MAX-ACCESS read-write
	STATUS     current
	DESCRIPTION 
		"TBD"
	::= { pppoe 5 }

-- PPPOE Access Concentrator Name

pppoeAccessConcentratorName  OBJECT-TYPE
	SYNTAX     DisplayString (SIZE(0..32))
	MAX-ACCESS read-write
	STATUS     current
	DESCRIPTION 
		"TBD"
	::= { pppoe 6 }

-- PPPOE Username

pppoeUserName  OBJECT-TYPE
	SYNTAX     DisplayString (SIZE(4..32))
	MAX-ACCESS read-write
	STATUS     current
	DESCRIPTION 
		"TBD"
	::= { pppoe 7 }

-- PPPOE Password

pppoePassword  OBJECT-TYPE
	SYNTAX     Password
	MAX-ACCESS read-write
	STATUS     current
	DESCRIPTION 
		"TBD"
	::= { pppoe 8 }

-- PPPOE Client IP address

pppoeClientIP  OBJECT-TYPE
	SYNTAX     IpAddress
	MAX-ACCESS read-only
	STATUS     current
	DESCRIPTION 
		"TBD"
	::= { pppoe 9 }

-- PPPOE Server IP address

pppoeServerIp  OBJECT-TYPE
	SYNTAX     IpAddress
	MAX-ACCESS read-only
	STATUS     current
	DESCRIPTION 
		"TBD"
	::= { pppoe 10 }

-- PPPOE Link Status

pppoeLinkStatus  OBJECT-TYPE
	SYNTAX     INTEGER {
		connected (1),
		connecting (2),
		disconnected (3)
	}
	MAX-ACCESS read-only
	STATUS     current
	DESCRIPTION 
		"TBD"
	::= { pppoe 11 }

-- PPPOE Session Restart

pppoeSessionRestart  OBJECT-TYPE
	SYNTAX     INTEGER {
		yes (1),
		no (2)
	}
	MAX-ACCESS read-write
	STATUS     current
	DESCRIPTION 
		"TBD"
	::= { pppoe 12 }

-- PPPOE MPPE Status

pppoeMPPEStatus  OBJECT-TYPE
	SYNTAX     INTEGER {
		mandatory (1),
		optional (2),
		disable (3)
	}
	MAX-ACCESS read-write
	STATUS     current
	DESCRIPTION 
		"TBD"
	DEFVAL  { optional }
	::= { pppoe 13 }

-- PPPOE MPPE Stateless

pppoeMPPEStateless  OBJECT-TYPE
	SYNTAX     INTEGER {
		enable (1),
		disable (2)
	}
	MAX-ACCESS read-write
	STATUS     current
	DESCRIPTION 
		"TBD"
	DEFVAL  { disable }
	::= { pppoe 14 }

-- PPPOE MPPE Status

pppoeMPPEKeyLength  OBJECT-TYPE
	SYNTAX     INTEGER {
		keyLength40Bit (1),
		keyLength56Bit (2),
		keyLength128Bit (3)
	}
	MAX-ACCESS read-write
	STATUS     current
	DESCRIPTION 
		"TBD"
	DEFVAL  { keyLength128Bit }
	::= { pppoe 15 }

-- PPPOE ConnectionAttempts

pppoeConnectionAttempts  OBJECT-TYPE
	SYNTAX     Unsigned32
	MAX-ACCESS read-write
	STATUS     current
	DESCRIPTION 
		"TBD"
	::= { pppoe 16 }

-- PPPOE ConnectionSuccess

pppoeConnectionSuccess  OBJECT-TYPE
	SYNTAX     Unsigned32
	MAX-ACCESS read-write
	STATUS     current
	DESCRIPTION 
		"TBD"
	::= { pppoe 17 }

-- VLAN Group Objects : vlan
-- ======================================================================================	
-- VLAN Status

vlanStatus  OBJECT-TYPE
	SYNTAX     INTEGER {
		enable (1),
		disable (2)
	}
	MAX-ACCESS read-write
	STATUS     current
	DESCRIPTION 
		"This parameter is used to configure the VLAN functionality. Select 
		 1 to enable the VLAN functionality and 
		 2 to disable the VLAN functionality."
	DEFVAL  { disable }
	::= { vlan 1 }

-- Management VLAN Identifier

mgmtVLANIdentifier  OBJECT-TYPE
	SYNTAX     VlanId
	MAX-ACCESS read-write
	STATUS     current
	DESCRIPTION 
		"This parameter represents the management VLAN Identifier (ID)."
	DEFVAL  { -1 }
	::= { vlan 2 }

-- Management VLAN Priority

mgmtVLANPriority  OBJECT-TYPE
	SYNTAX     Unsigned32 (0..7)
	MAX-ACCESS read-write
	STATUS     current
	DESCRIPTION 
		"This parameter represents the management VLAN priority, giving eight (2^3) priority 
		  levels with the highest priority as seven."
	DEFVAL  { 0 }
	::= { vlan 3 }

-- VLAN Ethernet Configuration Table 

vlanEthCfgTable  OBJECT-TYPE
	SYNTAX SEQUENCE OF VlanEthCfgTableEntry
	MAX-ACCESS not-accessible
	STATUS     current
	DESCRIPTION 
		"This table is used to configure the VLAN parameters for the ethernet
		  interface."
	::= { vlan 4 }

vlanEthCfgTableEntry  OBJECT-TYPE
	SYNTAX 	VlanEthCfgTableEntry
	MAX-ACCESS not-accessible
	STATUS     current
	DESCRIPTION 
		"This parameter represents the entry for the Vlan Configuration
		table."
	INDEX { vlanEthCfgTableIndex }
	::= { vlanEthCfgTable 1 }

VlanEthCfgTableEntry ::= SEQUENCE {
	vlanEthCfgTableIndex
		Unsigned32,
	vlanMode
		INTEGER,
	accessVLANId
		VlanId,
	accessVLANPriority
		Unsigned32,
	untaggedFrames
		INTEGER,
	portVLANID
		VlanId,
	portVLANPriority
		Unsigned32,
	allowUntaggedMgmtAccess
		INTEGER
}

vlanEthCfgTableIndex  OBJECT-TYPE
	SYNTAX     Unsigned32 (1)
	MAX-ACCESS read-only
	STATUS     current
	DESCRIPTION 
		"This parameter represents the physical interface and used as index to this table."
	::= { vlanEthCfgTableEntry 1 }

vlanMode  OBJECT-TYPE
	SYNTAX     INTEGER {
		transparent (1),
		access (2),
		trunk (3)
	}
	MAX-ACCESS read-write
	STATUS     current
	DESCRIPTION 
		"This parameter is used to set the VLAN Mode for the physical interface."
	DEFVAL  { transparent }
	::= { vlanEthCfgTableEntry 2 }

accessVLANId  OBJECT-TYPE
	SYNTAX     VlanId
	MAX-ACCESS read-write
	STATUS     current
	DESCRIPTION 
		"This parameter is used to set the access VlanId for the physical interface."
	DEFVAL  { -1 }
	::= { vlanEthCfgTableEntry 3 }

accessVLANPriority  OBJECT-TYPE
	SYNTAX     Unsigned32 (0..7)
	MAX-ACCESS read-write
	STATUS     current
	DESCRIPTION 
		"This parameter is used to set the access Vlan priority, which varies from 0 to 7 with
		                 7 having highest priority."
	DEFVAL  { 0 }
	::= { vlanEthCfgTableEntry 4 }

untaggedFrames  OBJECT-TYPE
	SYNTAX     INTEGER {
		enable (1),
		disable (2)
	}
	MAX-ACCESS read-write
	STATUS     current
	DESCRIPTION 
		"This parameter is used to set the option to allow the untagged frames."
	DEFVAL  { disable }
	::= { vlanEthCfgTableEntry 5 }

portVLANID  OBJECT-TYPE
	SYNTAX     VlanId
	MAX-ACCESS read-write
	STATUS     current
	DESCRIPTION 
		"TBD."
	DEFVAL  { -1 }
	::= { vlanEthCfgTableEntry 6 }

portVLANPriority  OBJECT-TYPE
	SYNTAX     Unsigned32 (0..7)
	MAX-ACCESS read-write
	STATUS     current
	DESCRIPTION 
		"TBD."
	DEFVAL  { 0 }
	::= { vlanEthCfgTableEntry 7 }

allowUntaggedMgmtAccess  OBJECT-TYPE
	SYNTAX     INTEGER {
		enable (1),
		disable (2)
	}
	MAX-ACCESS read-write
	STATUS     current
	DESCRIPTION 
		""
	DEFVAL  { disable }
	::= { vlanEthCfgTableEntry 8 }

-- VLAN Trunk Table 

vlanEthTrunkTable  OBJECT-TYPE
	SYNTAX SEQUENCE OF VlanEthTrunkTableEntry
	MAX-ACCESS not-accessible
	STATUS     current
	DESCRIPTION 
		"This table is used to configure the VLAN trunk parameters for ethernet 
		                 interface."
	::= { vlan 5 }

vlanEthTrunkTableEntry  OBJECT-TYPE
	SYNTAX 	VlanEthTrunkTableEntry
	MAX-ACCESS not-accessible
	STATUS     current
	DESCRIPTION 
		"This parameter represents the entry for the Vlan Trunk Configuration
		                 table."
	INDEX { vlanEthTrunkTableIndex, 
		vlanEthTrunkTableSecIndex }
	::= { vlanEthTrunkTable 1 }

VlanEthTrunkTableEntry ::= SEQUENCE {
	vlanEthTrunkTableIndex
		Unsigned32,
	vlanEthTrunkTableSecIndex
		Unsigned32,
	ethVLANTrunkId
		VlanId,
	vlanEthTrunkTableEntryStatus
		RowStatus
}

vlanEthTrunkTableIndex  OBJECT-TYPE
	SYNTAX     Unsigned32 (1..2)
	MAX-ACCESS read-only
	STATUS     current
	DESCRIPTION 
		"This parameter represents the vlan trunk table index and also
		                 represents the ethernet interface."
	::= { vlanEthTrunkTableEntry 1 }

vlanEthTrunkTableSecIndex  OBJECT-TYPE
	SYNTAX     Unsigned32 (1..256)
	MAX-ACCESS read-only
	STATUS     current
	DESCRIPTION 
		"This parameter represents the trunk table secondary index."
	::= { vlanEthTrunkTableEntry 2 }

ethVLANTrunkId  OBJECT-TYPE
	SYNTAX     VlanId
	MAX-ACCESS read-write
	STATUS     current
	DESCRIPTION 
		"This parameter is used to set the trunk id."
	::= { vlanEthTrunkTableEntry 3 }

vlanEthTrunkTableEntryStatus  OBJECT-TYPE
	SYNTAX     RowStatus
	MAX-ACCESS read-write
	STATUS     current
	DESCRIPTION 
		"This parameter is used to configure the vlan trunk table status. 
		 It can be configured as 
		                 active(enable) -1, 
		                 notInService(disable) - 2, 
		                 createAndGo(create row) -4, 
		                 destroy(delete) - 6"
	::= { vlanEthTrunkTableEntry 4 }

qinqStatus  OBJECT-TYPE
	SYNTAX     INTEGER {
		enable (1),
		disable (2)
	}
	MAX-ACCESS read-write
	STATUS     current
	DESCRIPTION 
		"TBD."
	DEFVAL  { disable }
	::= { vlan 6 }

tagProtocolID  OBJECT-TYPE
	SYNTAX     INTEGER {
		x8100 (1),
		x9100 (2),
		x88a8 (3)
	}
	MAX-ACCESS read-write
	STATUS     current
	DESCRIPTION 
		"TBD."
	DEFVAL  { x8100 }
	::= { vlan 7 }

serviceProviderVLANID  OBJECT-TYPE
	SYNTAX     VlanId
	MAX-ACCESS read-write
	STATUS     current
	DESCRIPTION 
		"TBD."
	DEFVAL  { 0 }
	::= { vlan 8 }

serviceProviderVLANPriority  OBJECT-TYPE
	SYNTAX     Unsigned32 (0..7)
	MAX-ACCESS read-write
	STATUS     current
	DESCRIPTION 
		"TBD."
	DEFVAL  { 0 }
	::= { vlan 9 }

-- ======================================================================================
--  Filtering Group Objects : filtering
-- ======================================================================================	
-- Filtering Control

filteringCtrl  OBJECT-TYPE
	SYNTAX     INTEGER {
		enable (1),
		disable (2)
	}
	MAX-ACCESS read-write
	STATUS     current
	DESCRIPTION 
		"This parameter stores the information whether the Global Filterng is 
		 Enabled or Disabled. If this parameter is set to enabled, then the 
		 filtering is enabled. If this parameter is disabled, then  filtering will 
		 be disabled. Select 
		 1 to enable this parameter and 
		 2 to disable this parameter."
	DEFVAL  { disable }
	::= { filtering 1 }

-- IntraBSS Filtering

intraBSSFiltering  OBJECT-TYPE
	SYNTAX     INTEGER {
		enable (1),
		disable (2)
	}
	MAX-ACCESS read-write
	STATUS     current
	DESCRIPTION 
		"This parameter controls the wireless to wireless communication. 
		 If this parameter is set to enabled, then wireless to wireless communication
		 is not allowed. If this parameter is set disabled, then wireless to 
		 wireless communication is allowed. Select 
		 1 to enable the wireless to wireless communication and 
		 2 to disable wireless to wireless communication."
	DEFVAL  { disable }
	::= { filtering 2 }

-- ======================================================================================
--  Protocol Filter Subgroup Objects : protocolFilter
-- ======================================================================================	
-- Ethernet Protocol Filter Control

etherProtocolFilteringCtrl  OBJECT-TYPE
	SYNTAX     INTEGER {
		ethernet (1),
		wireless (2),
		allInterfaces (3),
		disable (4)
	}
	MAX-ACCESS read-write
	STATUS     current
	DESCRIPTION 
		" This parameter is used to configure the interface.  By default, 
		  the parameter is set to disabled. The filter can be enabled either for Ethernet, 
		  Wireless or  All Interface. Select 
		  1 for ethernet, 
		  2 for wireless, 
		  3 for all interfaces and 
		  4 for disable."
	DEFVAL  { disable }
	::= { protocolFilter 1 }

-- Ethernet Protocol Filter Table Type

etherProtocolFilteringType  OBJECT-TYPE
	SYNTAX     INTEGER {
		passthru (1),
		block (2)
	}
	MAX-ACCESS read-write
	STATUS     current
	DESCRIPTION 
		"If the specific protocol is not available in the ethernet protocol table,
		 then this parameter specifies the action that needs to be taken on the packet.
		 If this parameter is set to passthru (1), then specific protocol will be allowed.
		 If this parameter is set to block (2), then specific protocol will be denied. 
		 "
	DEFVAL  { passthru }
	::= { protocolFilter 2 }

-- Ethernet Protocol Filtering Control Table

etherProtocolFilterTable  OBJECT-TYPE
	SYNTAX SEQUENCE OF EtherProtocolFilterTableEntry
	MAX-ACCESS not-accessible
	STATUS     current
	DESCRIPTION 
		"This table contains the two byte hexadecimal values of the  
		         protocols. The packets whose protocol field matches with any of  
		         the entries in this table will be forwarded or dropped."
	::= { protocolFilter 3 }

etherProtocolFilterTableEntry  OBJECT-TYPE
	SYNTAX 	EtherProtocolFilterTableEntry
	MAX-ACCESS not-accessible
	STATUS     current
	DESCRIPTION 
		"This parameter represents an entry in the protocol filter table.
		 This table supports upto 64 entries."
	INDEX { etherProtocolFilterTableIndex }
	::= { etherProtocolFilterTable 1 }

EtherProtocolFilterTableEntry ::= SEQUENCE {
	etherProtocolFilterTableIndex
		Unsigned32,
	etherProtocolFilterProtocolName
		DisplayString,
	etherProtocolFilterProtocolNumber
		OCTET STRING,
	etherprotocolFilterStatus
		INTEGER,
	etherProtocolFilterTableStatus
		RowStatus
}

etherProtocolFilterTableIndex  OBJECT-TYPE
	SYNTAX     Unsigned32 (1..64)
	MAX-ACCESS read-only
	STATUS     current
	DESCRIPTION 
		"This parameter represents the index of the ethernet protocol Filtering table."
	::= { etherProtocolFilterTableEntry 1 }

etherProtocolFilterProtocolName  OBJECT-TYPE
	SYNTAX     DisplayString (SIZE(1..32))
	MAX-ACCESS read-write
	STATUS     current
	DESCRIPTION 
		"This parameter represents a two byte hexadecimal value for the Ethernet 
		 protocol to be filtered."
	::= { etherProtocolFilterTableEntry 2 }

etherProtocolFilterProtocolNumber  OBJECT-TYPE
	SYNTAX     OCTET STRING
	MAX-ACCESS read-write
	STATUS     current
	DESCRIPTION 
		"This parameter represents the value in the protocol field of the  
		         Ethernet packet. The value is of 4-digit Hex format.  
		         Example:
		                 The value of IP protocol is 0800.  
		                The value of ARP protocol is 0806."
	::= { etherProtocolFilterTableEntry 3 }

etherprotocolFilterStatus  OBJECT-TYPE
	SYNTAX     INTEGER {
		block (1),
		passthru (2)
	}
	MAX-ACCESS read-write
	STATUS     current
	DESCRIPTION 
		"This parameter is used to configure the status of the ethernet
		 protocol filtering. Select 
		 1 to block,
		 2 to passthru."
	::= { etherProtocolFilterTableEntry 4 }

etherProtocolFilterTableStatus  OBJECT-TYPE
	SYNTAX     RowStatus
	MAX-ACCESS read-write
	STATUS     current
	DESCRIPTION 
		"This parameter is used to configure the ethernet protocol filtering
		 table status. 
		 It can be configured as 
		                 active(enable) -1, 
		                 notInService(disable) - 2, 
		                 createAndGo(create row) -4, 
		                 destroy(delete) - 6"
	DEFVAL  { notInService }
	::= { etherProtocolFilterTableEntry 5 }

-- Static MAC Address Filter Table

staticMACAddrFilterTable  OBJECT-TYPE
	SYNTAX SEQUENCE OF StaticMACAddrFilterTableEntry
	MAX-ACCESS not-accessible
	STATUS     current
	DESCRIPTION 
		"This table provides the MAC address of the stations on the wired  
		         and the wireless interface; the MAC addresses will be given in  
		         pairs.  Stations listed in the Static MAC Address filter will  
		         have no traffic forwarded by the device.  This way Multicast  
		         traffic exchanged between stations or servers can be prevented,  
		         from being transmitted over the wireless medium when both stations  
		         are actually located on the wired backbone."
	::= { staticMACAddrFilter 1 }

staticMACAddrFilterTableEntry  OBJECT-TYPE
	SYNTAX 	StaticMACAddrFilterTableEntry
	MAX-ACCESS not-accessible
	STATUS     current
	DESCRIPTION 
		"This parameter identifies the entry in the Static MAC address  
		         filter table. This table support upto 200 entries."
	INDEX { staticMACAddrFilterTableIndex }
	::= { staticMACAddrFilterTable 1 }

StaticMACAddrFilterTableEntry ::= SEQUENCE {
	staticMACAddrFilterTableIndex
		Unsigned32,
	staticMACAddrFilterWiredMACAddress
		MacAddress,
	staticMACAddrFilterWiredMACMask
		MacAddress,
	staticMACAddrFilterWirelessMACAddress
		MacAddress,
	staticMACAddrFilterWirelessMACMask
		MacAddress,
	staticMACAddrFilterComment
		DisplayString,
	staticMACAddrFilterTableEntryStatus
		RowStatus
}

staticMACAddrFilterTableIndex  OBJECT-TYPE
	SYNTAX     Unsigned32 (1..200)
	MAX-ACCESS read-only
	STATUS     current
	DESCRIPTION 
		"This parameter is user defined that represents the index of 
		 the Static MAC Filtering table."
	::= { staticMACAddrFilterTableEntry 1 }

staticMACAddrFilterWiredMACAddress  OBJECT-TYPE
	SYNTAX     MacAddress
	MAX-ACCESS read-write
	STATUS     current
	DESCRIPTION 
		"This parameter represents the MAC address of the station on the  
		         wired interface of the device."
	::= { staticMACAddrFilterTableEntry 2 }

staticMACAddrFilterWiredMACMask  OBJECT-TYPE
	SYNTAX     MacAddress
	MAX-ACCESS read-write
	STATUS     current
	DESCRIPTION 
		"This parameter represents the MAC address of the filter wired MASK."
	::= { staticMACAddrFilterTableEntry 3 }

staticMACAddrFilterWirelessMACAddress  OBJECT-TYPE
	SYNTAX     MacAddress
	MAX-ACCESS read-write
	STATUS     current
	DESCRIPTION 
		"This parameter represents the MAC address for the wireless interface."
	::= { staticMACAddrFilterTableEntry 4 }

staticMACAddrFilterWirelessMACMask  OBJECT-TYPE
	SYNTAX     MacAddress
	MAX-ACCESS read-write
	STATUS     current
	DESCRIPTION 
		"This parameter represents the mask for the wireless interface MAC address."
	::= { staticMACAddrFilterTableEntry 5 }

staticMACAddrFilterComment  OBJECT-TYPE
	SYNTAX     DisplayString (SIZE(0..32))
	MAX-ACCESS read-write
	STATUS     current
	DESCRIPTION 
		"This parameter is used for an optional comment associated to 
		 the staticMACAddrFilter entry."
	::= { staticMACAddrFilterTableEntry 6 }

staticMACAddrFilterTableEntryStatus  OBJECT-TYPE
	SYNTAX     RowStatus
	MAX-ACCESS read-create
	STATUS     current
	DESCRIPTION 
		"This parameter is used to configure the status of the staticMACAddrFilterTable. Select 
		 It can be configured as 
		                 active(enable) -1, 
		                 notInService(disable) - 2, 
		                 createAndGo(create row) -4, 
		                 destroy(delete) - 6"
	DEFVAL  { active }
	::= { staticMACAddrFilterTableEntry 7 }

-- Advanced Filtering Table

advancedFilterTable  OBJECT-TYPE
	SYNTAX SEQUENCE OF AdvancedFilterTableEntry
	MAX-ACCESS not-accessible
	STATUS     current
	DESCRIPTION 
		"This table is used to configure the advanced filtering using
		 protocol name and direction."
	::= { advancedFiltering 1 }

advancedFilterTableEntry  OBJECT-TYPE
	SYNTAX 	AdvancedFilterTableEntry
	MAX-ACCESS not-accessible
	STATUS     current
	DESCRIPTION 
		"This parameter represents the entry for advancedFilterTable. 
		 This table supports up to 5 entries."
	INDEX { advancedFilterTableIndex }
	::= { advancedFilterTable 1 }

AdvancedFilterTableEntry ::= SEQUENCE {
	advancedFilterTableIndex
		Unsigned32,
	advancedFilterProtocolName
		DisplayString,
	advancedFilterDirection
		INTEGER,
	advancedFilterTableEntryStatus
		RowStatus
}

advancedFilterTableIndex  OBJECT-TYPE
	SYNTAX     Unsigned32 (1..5)
	MAX-ACCESS read-only
	STATUS     current
	DESCRIPTION 
		"This parameter represents the index of the advanced filtering table."
	::= { advancedFilterTableEntry 1 }

advancedFilterProtocolName  OBJECT-TYPE
	SYNTAX     DisplayString
	MAX-ACCESS read-only
	STATUS     current
	DESCRIPTION 
		"This parameter represents the protocol name to be filtered. (DenyIPX RIP, 
		 Deny IPX SAP, Deny IPX LSP, Deny IP Broadcasts, Deny IP Multicasts)"
	::= { advancedFilterTableEntry 2 }

advancedFilterDirection  OBJECT-TYPE
	SYNTAX     INTEGER {
		ethernet2wireless (1),
		wireless2ethernet (2),
		both (3)
	}
	MAX-ACCESS read-write
	STATUS     current
	DESCRIPTION 
		"This parameter represents the direction of the individual entry in 
		 the advanced filter table. The direction can be enabled either for 
		 Ethernet to Wireless, Wireless to Ethernet or both. Select 
		 1 for ethernet2wireless, 
		 2 for wireless2ethernet, 
		 3 for both."
	DEFVAL  { both }
	::= { advancedFilterTableEntry 3 }

advancedFilterTableEntryStatus  OBJECT-TYPE
	SYNTAX     RowStatus
	MAX-ACCESS read-write
	STATUS     current
	DESCRIPTION 
		"This parameter is used to configure the row status of the advanced 
		 filtering table. 
		                 It can be configured as 
		                 active(enable) -1, 
		                 notInService(disable) - 2, 
		                 createAndGo(create row) -4, 
		                 destroy(delete) - 6"
	DEFVAL  { notInService }
	::= { advancedFilterTableEntry 4 }

-- TCP UDP Port Filter Control

tcpudpPortFilterCtrl  OBJECT-TYPE
	SYNTAX     INTEGER {
		enable (1),
		disable (2)
	}
	MAX-ACCESS read-write
	STATUS     current
	DESCRIPTION 
		"This parameter is used to configure the Tcp Udp Port Filtering. 
		 Select 
		 1 to enable and 
		 2 to disable the Tcp Udp Port Filtering. "
	DEFVAL  { disable }
	::= { tcpudpPortFilter 1 }

-- TCP UDP Port Filter Table

tcpudpPortFilterTable  OBJECT-TYPE
	SYNTAX SEQUENCE OF TcpudpPortFilterTableEntry
	MAX-ACCESS not-accessible
	STATUS     current
	DESCRIPTION 
		"This table contains the configurations for the Tcp Udp Port Filtering table."
	::= { tcpudpPortFilter 2 }

tcpudpPortFilterTableEntry  OBJECT-TYPE
	SYNTAX 	TcpudpPortFilterTableEntry
	MAX-ACCESS not-accessible
	STATUS     current
	DESCRIPTION 
		"This parameter represents the entry for tcpudpPortFilterTable. 
		 This table supports up to 64 entries."
	INDEX { tcpudpPortFilterTableIndex }
	::= { tcpudpPortFilterTable 1 }

TcpudpPortFilterTableEntry ::= SEQUENCE {
	tcpudpPortFilterTableIndex
		Unsigned32,
	tcpudpPortFilterProtocolName
		DisplayString,
	tcpudpPortFilterPortNumber
		Unsigned32,
	tcpudpPortFilterPortType
		INTEGER,
	tcpudpPortFilterInterface
		INTEGER,
	tcpudpPortFilterTableEntryStatus
		RowStatus
}

tcpudpPortFilterTableIndex  OBJECT-TYPE
	SYNTAX     Unsigned32 (1..64)
	MAX-ACCESS read-only
	STATUS     current
	DESCRIPTION 
		"This parameter is used as index for the TcpUdp port filter table."
	::= { tcpudpPortFilterTableEntry 1 }

tcpudpPortFilterProtocolName  OBJECT-TYPE
	SYNTAX     DisplayString (SIZE(1..32))
	MAX-ACCESS read-write
	STATUS     current
	DESCRIPTION 
		"This parameter represents the protocol name for the tcpudpPortFilter."
	::= { tcpudpPortFilterTableEntry 2 }

tcpudpPortFilterPortNumber  OBJECT-TYPE
	SYNTAX     Unsigned32
	MAX-ACCESS read-write
	STATUS     current
	DESCRIPTION 
		"This parameter represents the Port number for the tcpudpPortFilter."
	::= { tcpudpPortFilterTableEntry 3 }

tcpudpPortFilterPortType  OBJECT-TYPE
	SYNTAX     INTEGER {
		tcp (1),
		udp (2),
		both (3)
	}
	MAX-ACCESS read-write
	STATUS     current
	DESCRIPTION 
		"This parameter represents the port type for this TcpUdp Port filter table. 
		 The parameter can be either TCP or UDP or TCP/UDP. Select 
		 1 for TCP, 
		 2 for UDP and 
		 3 for both."
	DEFVAL  { both }
	::= { tcpudpPortFilterTableEntry 4 }

tcpudpPortFilterInterface  OBJECT-TYPE
	SYNTAX     INTEGER {
		onlyEthernet (1),
		onlyWireless (2),
		allInterfaces (3)
	}
	MAX-ACCESS read-write
	STATUS     current
	DESCRIPTION 
		"This parameter is used to configure the interface. By default, the parameter 
		 is set to All Interfaces. The filter can be enabled either for Ethernet, 
		 Wireless or  All Interface. Select 
		 1 for only Ethernet, 
		 2 for only Wireless and 
		 3 for allInterfaces."
	DEFVAL  { allInterfaces }
	::= { tcpudpPortFilterTableEntry 5 }

tcpudpPortFilterTableEntryStatus  OBJECT-TYPE
	SYNTAX     RowStatus
	MAX-ACCESS read-create
	STATUS     current
	DESCRIPTION 
		"The parameter indicates the status of the TCP/UDP portfilter table entry.
		                 It can be configured as 
		                 active(enable) -1, 
		                 notInService(disable) - 2, 
		                 createAndGo(create row) -4, 
		                 destroy(delete) - 6)"
	::= { tcpudpPortFilterTableEntry 6 }

-- =============================================================================
-- The IntraCellBlocking Subgroup
-- =============================================================================

worpIntraCellBlockingStatus  OBJECT-TYPE
	SYNTAX     INTEGER {
		enable (1),
		disable (2)
	}
	MAX-ACCESS read-write
	STATUS     current
	DESCRIPTION 
		"This parameter is used to enable/disable IntraCell Blocking/Filtering."
	DEFVAL  { disable }
	::= { worpIntraCellBlocking 1 }

-- WORP Intra Cell Blocking Group

worpIntraCellBlockingMACTable  OBJECT-TYPE
	SYNTAX SEQUENCE OF WorpIntraCellBlockingMACTableEntry
	MAX-ACCESS not-accessible
	STATUS     current
	DESCRIPTION 
		"The MAC table entries for IntraCell Blocking filters.  This table 
		can hold up to a maximum of 250 entries."
	::= { worpIntraCellBlocking 2 }

worpIntraCellBlockingMACTableEntry  OBJECT-TYPE
	SYNTAX 	WorpIntraCellBlockingMACTableEntry
	MAX-ACCESS not-accessible
	STATUS     current
	DESCRIPTION 
		"This parameter represents the entry in the IntraCell Blocking MAC Table."
	INDEX { worpIntraCellBlockingMACTableIndex }
	::= { worpIntraCellBlockingMACTable 1 }

WorpIntraCellBlockingMACTableEntry ::= SEQUENCE {
	worpIntraCellBlockingMACTableIndex
		Unsigned32,
	worpIntraCellBlockingMACAddress
		MacAddress,
	worpIntraCellBlockingGroupID1
		INTEGER,
	worpIntraCellBlockingGroupID2
		INTEGER,
	worpIntraCellBlockingGroupID3
		INTEGER,
	worpIntraCellBlockingGroupID4
		INTEGER,
	worpIntraCellBlockingGroupID5
		INTEGER,
	worpIntraCellBlockingGroupID6
		INTEGER,
	worpIntraCellBlockingGroupID7
		INTEGER,
	worpIntraCellBlockingGroupID8
		INTEGER,
	worpIntraCellBlockingGroupID9
		INTEGER,
	worpIntraCellBlockingGroupID10
		INTEGER,
	worpIntraCellBlockingGroupID11
		INTEGER,
	worpIntraCellBlockingGroupID12
		INTEGER,
	worpIntraCellBlockingGroupID13
		INTEGER,
	worpIntraCellBlockingGroupID14
		INTEGER,
	worpIntraCellBlockingGroupID15
		INTEGER,
	worpIntraCellBlockingGroupID16
		INTEGER,
	worpIntraCellBlockingMACTableEntryStatus
		RowStatus
}

worpIntraCellBlockingMACTableIndex  OBJECT-TYPE
	SYNTAX     Unsigned32 (1..250)
	MAX-ACCESS read-only
	STATUS     current
	DESCRIPTION 
		"This parameter is used as the index to the IntraCell Blocking MAC Table."
	::= { worpIntraCellBlockingMACTableEntry 1 }

worpIntraCellBlockingMACAddress  OBJECT-TYPE
	SYNTAX     MacAddress
	MAX-ACCESS read-write
	STATUS     current
	DESCRIPTION 
		"This parameter represents the MAC address of the SU which is allowed to 
		        communicate with other SUs with the same group ID."
	::= { worpIntraCellBlockingMACTableEntry 2 }

worpIntraCellBlockingGroupID1  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 3 }

worpIntraCellBlockingGroupID2  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 4 }

worpIntraCellBlockingGroupID3  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 5 }

worpIntraCellBlockingGroupID4  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 6 }

worpIntraCellBlockingGroupID5  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 7 }

worpIntraCellBlockingGroupID6  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 8 }

worpIntraCellBlockingGroupID7  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 9 }

worpIntraCellBlockingGroupID8  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 10 }

worpIntraCellBlockingGroupID9  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 11 }

worpIntraCellBlockingGroupID10  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 12 }

worpIntraCellBlockingGroupID11  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 13 }

worpIntraCellBlockingGroupID12  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 14 }

worpIntraCellBlockingGroupID13  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 15 }

worpIntraCellBlockingGroupID14  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 16 }

worpIntraCellBlockingGroupID15  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 17 }

worpIntraCellBlockingGroupID16  OBJECT-TYPE
	SYNTAX     INTEGER {
		enable (1),
		disable (2)
	}
	MAX-ACCESS read-write
	STATUS     current
	DESCRIPTION 
		"This parameter enables to segregate the SUs for intra/ inter cell communications."
	DEFVAL  { disable }
	::= { worpIntraCellBlockingMACTableEntry 18 }

worpIntraCellBlockingMACTableEntryStatus  OBJECT-TYPE
	SYNTAX     RowStatus
	MAX-ACCESS read-write
	STATUS     current
	DESCRIPTION 
		"This parameter is used to configure the row status for the worp Intra cell blocking
		                 MAC table. 
		                 It can be configured as 
		                 active(enable) -1, 
		                 notInService(disable) - 2, 
		                 createAndGo(create row) -4, 
		                 destroy(delete) - 6"
	DEFVAL  { active }
	::= { worpIntraCellBlockingMACTableEntry 19 }

-- WORP Intra Cell Blocking Group Table

worpIntraCellBlockingGroupTable  OBJECT-TYPE
	SYNTAX SEQUENCE OF WorpIntraCellBlockingGroupTableEntry
	MAX-ACCESS not-accessible
	STATUS     current
	DESCRIPTION 
		"This table holds the group entries for IntraCell Blocking."
	::= { worpIntraCellBlocking 3 }

worpIntraCellBlockingGroupTableEntry  OBJECT-TYPE
	SYNTAX 	WorpIntraCellBlockingGroupTableEntry
	MAX-ACCESS not-accessible
	STATUS     current
	DESCRIPTION 
		"This parameter represents the entry in the IntraCell Blocking 
		Group Table. This table can contain a maximum of 16 entries."
	INDEX { worpIntraCellBlockingGroupTableIndex }
	::= { worpIntraCellBlockingGroupTable 1 }

WorpIntraCellBlockingGroupTableEntry ::= SEQUENCE {
	worpIntraCellBlockingGroupTableIndex
		Unsigned32,
	worpIntraCellBlockingGroupName
		DisplayString,
	worpIntraCellBlockingGroupTableEntryStatus
		RowStatus
}

worpIntraCellBlockingGroupTableIndex  OBJECT-TYPE
	SYNTAX     Unsigned32 (1..16)
	MAX-ACCESS read-only
	STATUS     current
	DESCRIPTION 
		"This parameter is used as the index to the IntraCell Blocking 
		Group Table."
	::= { worpIntraCellBlockingGroupTableEntry 1 }

worpIntraCellBlockingGroupName  OBJECT-TYPE
	SYNTAX     DisplayString (SIZE(1..32))
	MAX-ACCESS read-write
	STATUS     current
	DESCRIPTION 
		"This parameter represents the group name."
	::= { worpIntraCellBlockingGroupTableEntry 2 }

worpIntraCellBlockingGroupTableEntryStatus  OBJECT-TYPE
	SYNTAX     RowStatus
	MAX-ACCESS read-write
	STATUS     current
	DESCRIPTION 
		"This parameter is used to enable, disable the IntraCell Blocking Group Table."
	DEFVAL  { notInService }
	::= { worpIntraCellBlockingGroupTableEntry 3 }

-- =============================================================================
-- The Security Gateway Subgroup: securityGateway
-- =============================================================================

securityGatewayStatus  OBJECT-TYPE
	SYNTAX     INTEGER {
		enable (1),
		disable (2)
	}
	MAX-ACCESS read-write
	STATUS     current
	DESCRIPTION 
		"This parameter is used to enable or disable security gateway feature."
	DEFVAL  { disable }
	::= { securityGateway 1 }

securityGatewayMacAddress  OBJECT-TYPE
	SYNTAX     MacAddress
	MAX-ACCESS read-write
	STATUS     current
	DESCRIPTION 
		"This parameter represents the security Gateway MAC Address to which all
		         frames will be forwarded by the device."
	::= { securityGateway 2 }

stpFrameForwardStatus  OBJECT-TYPE
	SYNTAX     INTEGER {
		enable (1),
		disable (2)
	}
	MAX-ACCESS read-write
	STATUS     current
	DESCRIPTION 
		"STP Frame forward status will block/allow the IEEE 802.1D and 802.1Q reserved MAC addresses (01:80:C2:00:00:00 to 01:80:C2:00:00:0F) 
		                 Select 1 to enable this parameter and 
		                        2 to disable this parameter."
	DEFVAL  { disable }
	::= { filtering 9 }

-- ============================================================================
-- The Storm Threshold Subgroup: stormThreshold
-- =============================================================================
-- Storm Threshold Table

stormThresholdTable  OBJECT-TYPE
	SYNTAX SEQUENCE OF StormThresholdTableEntry
	MAX-ACCESS not-accessible
	STATUS     current
	DESCRIPTION 
		" This table contains information on the threshold value
		  of the multicast and brodcast packects that can be 
		  processed for interface(s) present in the device ."
	::= { stormThreshold 1 }

stormThresholdTableEntry  OBJECT-TYPE
	SYNTAX 	StormThresholdTableEntry
	MAX-ACCESS not-accessible
	STATUS     current
	DESCRIPTION 
		"This parameter represents the entry in the storm threshold
		             table."
	INDEX { stormThresholdTableIndex }
	::= { stormThresholdTable 1 }

StormThresholdTableEntry ::= SEQUENCE {
	stormThresholdTableIndex
		Unsigned32,
	stormFilterInterface
		INTEGER,
	stormMulticastThreshold
		Integer32,
	stormBroadcastThreshold
		Integer32
}

stormThresholdTableIndex  OBJECT-TYPE
	SYNTAX     Unsigned32
	MAX-ACCESS read-only
	STATUS     current
	DESCRIPTION 
		"This parameter is used as index for the storm Threshold Table."
	::= { stormThresholdTableEntry 1 }

stormFilterInterface  OBJECT-TYPE
	SYNTAX     INTEGER {
		ethernet (1),
		wireless (2)
	}
	MAX-ACCESS read-only
	STATUS     current
	DESCRIPTION 
		"This parameter is used to configure the interface.The filter can be enabled
		             either for Ethernet or Wireless.
		  1 for Ethernet  
		  2 for Wireless"
	DEFVAL  { ethernet }
	::= { stormThresholdTableEntry 2 }

stormMulticastThreshold  OBJECT-TYPE
	SYNTAX     Integer32 (0..65536)
	MAX-ACCESS read-write
	STATUS     current
	DESCRIPTION 
		" This parameter is used to provide the threshold value of the
		  multicast packets to be processed for the interface.
		  If threshold value for multicast packets is set to '0', no 
		  filtering will take place (filtering will be disabled).Excess
		  packets will be dropped if packets are more than threshold 
		  value.To disable MultiCast packets filtering for this interface
		  this variable should be set to '0'(zero)."
	DEFVAL  { 0 }
	::= { stormThresholdTableEntry 3 }

stormBroadcastThreshold  OBJECT-TYPE
	SYNTAX     Integer32 (0..65536)
	MAX-ACCESS read-write
	STATUS     current
	DESCRIPTION 
		" This parameter is used to provide the threshold value of the
		  broadcast packets to be processed for interface.If threshold
		  value for broadcast packets is set to '0', no filtering will
		        take place (filtering will be disabled).
		        Excess packets will be dropped if packets are more than 
		  threshold value.To disable Broadcast wireless packets filtering,this 
		  variable should be set to '0' (Zero)."
	DEFVAL  { 0 }
	::= { stormThresholdTableEntry 4 }

-- ======================================================================================
-- Definition of the DHCP Server subgroup Objects : dhcpServer
-- ======================================================================================       
-- DHCP Server Status

dhcpServerStatus  OBJECT-TYPE
	SYNTAX     INTEGER {
		disable (1),
		dhcpServer (2),
		dhcpRelayAgent (3)
	}
	MAX-ACCESS read-write
	STATUS     current
	DESCRIPTION 
		"This parameter indicates if the DHCP server/relay is enabled or disabled
		    in the device."
	DEFVAL  { disable }
	::= { dhcpServer 1 }

-- DHCP Max Lease Time

dhcpMaxLeaseTime  OBJECT-TYPE
	SYNTAX     TimeTicks
	MAX-ACCESS read-write
	STATUS     deprecated
	DESCRIPTION 
		"This parameter represents the maximum lease time in 100th seconds for 
		    the IP address assigned by the DHCP server to the DHCP client."
	DEFVAL  { 8640000 }
	::= { dhcpServer 2 }

-- DHCP Server Interface Table

dhcpServerIfTable  OBJECT-TYPE
	SYNTAX SEQUENCE OF DhcpServerIfTableEntry
	MAX-ACCESS not-accessible
	STATUS     current
	DESCRIPTION 
		"This table is used to configure the DHCP server for a particular interface."
	::= { dhcpServer 3 }

dhcpServerIfTableEntry  OBJECT-TYPE
	SYNTAX 	DhcpServerIfTableEntry
	MAX-ACCESS not-accessible
	STATUS     current
	DESCRIPTION 
		"This parameter represents the entry for the dhcpServerIfTable."
	INDEX { dhcpServerIfTableIndex }
	::= { dhcpServerIfTable 1 }

DhcpServerIfTableEntry ::= SEQUENCE {
	dhcpServerIfTableIndex
		Unsigned32,
	dhcpServerInterfaceType
		INTEGER,
	dhcpServerNetMask
		IpAddress,
	dhcpServerDefaultGateway
		IpAddress,
	dhcpServerPrimaryDNS
		IpAddress,
	dhcpServerSecondaryDNS
		IpAddress,
	dhcpServerDefaultLeaseTime
		TimeTicks,
	dhcpServerIfTableComment
		DisplayString,
	dhcpServerIfTableEntryStatus
		RowStatus,
	dhcpServerDefaultLeasePeriod
		Unsigned32
}

dhcpServerIfTableIndex  OBJECT-TYPE
	SYNTAX     Unsigned32 (1..5)
	MAX-ACCESS read-only
	STATUS     current
	DESCRIPTION 
		"This parameter represents the index for the dhcpServerIfTable."
	::= { dhcpServerIfTableEntry 1 }

dhcpServerInterfaceType  OBJECT-TYPE
	SYNTAX     INTEGER {
		bridge (1),
		ethernet1 (2),
		ethernet2 (3),
		wireless1 (4)
	}
	MAX-ACCESS read-only
	STATUS     current
	DESCRIPTION 
		"This parameter shows the list of interfaces for which the DHCP 
		                    can be configured."
	::= { dhcpServerIfTableEntry 2 }

dhcpServerNetMask  OBJECT-TYPE
	SYNTAX     IpAddress
	MAX-ACCESS read-write
	STATUS     current
	DESCRIPTION 
		"This parameter is used to configure the mask for the interface shown."
	::= { dhcpServerIfTableEntry 3 }

dhcpServerDefaultGateway  OBJECT-TYPE
	SYNTAX     IpAddress
	MAX-ACCESS read-write
	STATUS     current
	DESCRIPTION 
		"This parameter represents the IP Address of the gateway or router 
		that the DHCP Server will assign to the DHCP client."
	::= { dhcpServerIfTableEntry 4 }

dhcpServerPrimaryDNS  OBJECT-TYPE
	SYNTAX     IpAddress
	MAX-ACCESS read-write
	STATUS     current
	DESCRIPTION 
		"This parameter represents the primary DNS Server IP Address to be
		assinged to a DHCP Client."
	::= { dhcpServerIfTableEntry 5 }

dhcpServerSecondaryDNS  OBJECT-TYPE
	SYNTAX     IpAddress
	MAX-ACCESS read-write
	STATUS     current
	DESCRIPTION 
		"This parameter represents the secondary DNS Server IP Address to be
		    assinged to a DHCP Client."
	::= { dhcpServerIfTableEntry 6 }

dhcpServerDefaultLeaseTime  OBJECT-TYPE
	SYNTAX     TimeTicks
	MAX-ACCESS read-write
	STATUS     deprecated
	DESCRIPTION 
		"This parameter represents the default lease time, in 100th seconds, for 
		the IP address assigned by the DHCP server to the DHCP client."
	::= { dhcpServerIfTableEntry 7 }

dhcpServerIfTableComment  OBJECT-TYPE
	SYNTAX     DisplayString
	MAX-ACCESS read-write
	STATUS     current
	DESCRIPTION 
		"This parameter represents an optional comment for this table entry."
	::= { dhcpServerIfTableEntry 8 }

dhcpServerIfTableEntryStatus  OBJECT-TYPE
	SYNTAX     RowStatus
	MAX-ACCESS read-write
	STATUS     current
	DESCRIPTION 
		"This parameter is used to configure the row status for the dhcpServerIfTable. 
		                    It can be configured as 
		                    active(enable) -1, 
		                    notInService(disable) - 2, 
		                    createAndGo(create row) -4, 
		                    destroy(delete) - 6"
	::= { dhcpServerIfTableEntry 9 }

dhcpServerDefaultLeasePeriod  OBJECT-TYPE
	SYNTAX     Unsigned32 (3600..172800)
	MAX-ACCESS read-write
	STATUS     current
	DESCRIPTION 
		"This parameter represents the default lease time, in seconds, for 
		the IP address assigned by the DHCP server to the DHCP client."
	::= { dhcpServerIfTableEntry 10 }

-- DHCP Server IP Pool Table

dhcpServerIpPoolTable  OBJECT-TYPE
	SYNTAX SEQUENCE OF DhcpServerIpPoolTableEntry
	MAX-ACCESS not-accessible
	STATUS     current
	DESCRIPTION 
		"This table contains the pools of IP Addresses that the DHCP server 
		will assign to the DHCP clients."
	::= { dhcpServer 4 }

dhcpServerIpPoolTableEntry  OBJECT-TYPE
	SYNTAX 	DhcpServerIpPoolTableEntry
	MAX-ACCESS not-accessible
	STATUS     current
	DESCRIPTION 
		"This parameter represents entries in the dhcpServerIpPoolTable."
	INDEX { dhcpServerIpPoolTableIndex }
	::= { dhcpServerIpPoolTable 1 }

DhcpServerIpPoolTableEntry ::= SEQUENCE {
	dhcpServerIpPoolTableIndex
		Unsigned32,
	dhcpServerIpPoolInterface
		INTEGER,
	dhcpServerIpPoolStartIpAddress
		IpAddress,
	dhcpServerIpPoolEndIpAddress
		IpAddress,
	dhcpServerIpPoolTableEntryStatus
		RowStatus
}

dhcpServerIpPoolTableIndex  OBJECT-TYPE
	SYNTAX     Unsigned32 (1..5)
	MAX-ACCESS read-only
	STATUS     current
	DESCRIPTION 
		"This parameter is used as the index for the IP Address Pool table."
	::= { dhcpServerIpPoolTableEntry 1 }

dhcpServerIpPoolInterface  OBJECT-TYPE
	SYNTAX     INTEGER {
		bridge (1),
		ethernet1 (2),
		ethernet2 (3),
		wireless1 (4)
	}
	MAX-ACCESS read-write
	STATUS     current
	DESCRIPTION 
		"This parameter shows the list of interfaces for which the DHCP
		                    server can be configured."
	::= { dhcpServerIpPoolTableEntry 2 }

dhcpServerIpPoolStartIpAddress  OBJECT-TYPE
	SYNTAX     IpAddress
	MAX-ACCESS read-write
	STATUS     current
	DESCRIPTION 
		"This parameter represents the start IP address for this DHCP IP 
		        Address IP Pool Table entry."
	::= { dhcpServerIpPoolTableEntry 3 }

dhcpServerIpPoolEndIpAddress  OBJECT-TYPE
	SYNTAX     IpAddress
	MAX-ACCESS read-write
	STATUS     current
	DESCRIPTION 
		"This parameter represents the end IP address for this DHCP IP 
		        Address IP Pool Table entry."
	::= { dhcpServerIpPoolTableEntry 4 }

dhcpServerIpPoolTableEntryStatus  OBJECT-TYPE
	SYNTAX     RowStatus
	MAX-ACCESS read-write
	STATUS     current
	DESCRIPTION 
		"This parameter is used to configure the row status for the dhcpServerIpPoolTable. 
		                    It can be configured as 
		                    active(enable) -1, 
		                    notInService(disable) - 2, 
		                    createAndGo(create row) -4, 
		                    destroy(delete) - 6"
	::= { dhcpServerIpPoolTableEntry 5 }

-- DHCP Max Lease Period in Seconds

dhcpMaxLeasePeriod  OBJECT-TYPE
	SYNTAX     Unsigned32 (3600..172800)
	MAX-ACCESS read-write
	STATUS     current
	DESCRIPTION 
		"This parameter represents the maximum lease time in seconds for 
		    the IP address assigned by the DHCP server to the DHCP client."
	DEFVAL  { 86400 }
	::= { dhcpServer 5 }

-- ======================================================================================
-- Definition of the DHCP Relay subgroup Objects : dhcpRelay
-- ======================================================================================       
-- DHCP Relay Server Table

dhcpRelayServerTable  OBJECT-TYPE
	SYNTAX SEQUENCE OF DhcpRelayServerTableEntry
	MAX-ACCESS not-accessible
	STATUS     current
	DESCRIPTION 
		"This table contains a list of DHCP servers to which the
		DHCP Agent will communicate with."
	::= { dhcpRelay 1 }

dhcpRelayServerTableEntry  OBJECT-TYPE
	SYNTAX 	DhcpRelayServerTableEntry
	MAX-ACCESS not-accessible
	STATUS     current
	DESCRIPTION 
		"This parameter represents and entry in the DHCP Server table."
	INDEX { dhcpRelayServerTableIndex }
	::= { dhcpRelayServerTable 1 }

DhcpRelayServerTableEntry ::= SEQUENCE {
	dhcpRelayServerTableIndex
		Unsigned32,
	dhcpRelayServerIpAddress
		IpAddress,
	dhcpRelayServerTableEntryStatus
		RowStatus
}

dhcpRelayServerTableIndex  OBJECT-TYPE
	SYNTAX     Unsigned32
	MAX-ACCESS read-only
	STATUS     current
	DESCRIPTION 
		"This parameter is used as the index to this dhcpRelayServerTable."
	::= { dhcpRelayServerTableEntry 1 }

dhcpRelayServerIpAddress  OBJECT-TYPE
	SYNTAX     IpAddress
	MAX-ACCESS read-write
	STATUS     current
	DESCRIPTION 
		"This parameter represents the IP address of the DHCP server
		 that shall receive DHCP requests from the device."
	::= { dhcpRelayServerTableEntry 2 }

dhcpRelayServerTableEntryStatus  OBJECT-TYPE
	SYNTAX     RowStatus
	MAX-ACCESS read-write
	STATUS     current
	DESCRIPTION 
		"This parameter is used to configure the row status for the dhcpRelayServerTable. 
		                    It can be configured as 
		                    active(enable) -1, 
		                    notInService(disable) - 2, 
		                    createAndGo(create row) -4, 
		                    destroy(delete) - 6"
	::= { dhcpRelayServerTableEntry 3 }

-- ======================================================================================
-- Definition of the System Configuration Group objects
-- ======================================================================================	
-- System Type Table Group

sysTypeTable  OBJECT-TYPE
	SYNTAX SEQUENCE OF SysTypeTableEntry
	MAX-ACCESS not-accessible
	STATUS     current
	DESCRIPTION 
		"This table holds the information about the supported and current 
		                 modes of the device."
	::= { sysConf 1 }

sysTypeTableEntry  OBJECT-TYPE
	SYNTAX 	SysTypeTableEntry
	MAX-ACCESS not-accessible
	STATUS     current
	DESCRIPTION 
		"This parameter represents the entry status for the sysTypeTable. It can
		                 hold one entry."
	INDEX { sysTypeRadioIfIndex }
	::= { sysTypeTable 1 }

SysTypeTableEntry ::= SEQUENCE {
	sysTypeRadioIfIndex
		Unsigned32,
	sysTypeMode
		Unsigned32,
	sysTypeActiveMode
		Unsigned32,
	sysTypeSupportedMode
		DisplayString,
	sysTypeSupportedFreqDomains
		DisplayString,
	sysTypeFreqDomain
		INTEGER,
	sysTypeActiveFreqDomain
		INTEGER,
	sysConfFreqFilterLowerEdge
		Unsigned32,
	sysConfFreqFilterUpperEdge
		Unsigned32
}

sysTypeRadioIfIndex  OBJECT-TYPE
	SYNTAX     Unsigned32
	MAX-ACCESS read-only
	STATUS     current
	DESCRIPTION 
		"This parameter represents the physical interface (radio) and
		                 index for the sysType Table."
	::= { sysTypeTableEntry 1 }

sysTypeMode  OBJECT-TYPE
	SYNTAX     Unsigned32 (1..5)
	MAX-ACCESS read-write
	STATUS     current
	DESCRIPTION 
		"This parameter is used to configure the mode of the radio(s). Please 
		                 refer the sysTypeSupportedMode object for the supported modes. The modes
		                 are represented in numbers as follows:
		                 AP (1),
		                 CLIENT (2),
		                 WDS (3),
		                 BSU (4), *Applies in TMP(tsunamiMP) mode - please refer sysFeatureProductFamily*
		                 EndPointA (4), *Applies in QB(tsunamiQuickBridge) mode - please refer sysFeatureProductFamily*
		                 SU (5) *Applies in TMP(tsunamiMP) mode - please refer sysFeatureProductFamily* 
		                 EndPointB (5) *Applies in QB(tsunamiQuickBridge) mode - please refer sysFeatureProductFamily*"
	DEFVAL  { 1 }
	::= { sysTypeTableEntry 2 }

sysTypeActiveMode  OBJECT-TYPE
	SYNTAX     Unsigned32 (1..5)
	MAX-ACCESS read-only
	STATUS     current
	DESCRIPTION 
		"This parameter shows the active mode of the radio(s). The configured mode
		                 will take effect after the reboot.  The modes are represented in numbers 
		                 as follows:
		                 AP (1),
		                 CLIENT (2),
		                 WDS (3),
		                 BSU (4), *Applies in TMP(tsunamiMP) mode - please refer sysFeatureProductFamily*
		                 EndPointA (4), *Applies in QB(tsunamiQuickBridge) mode - please refer sysFeatureProductFamily*
		                 SU (5) *Applies in TMP(tsunamiMP) mode - please refer sysFeatureProductFamily* 
		                 EndPointB (5) *Applies in QB(tsunamiQuickBridge) mode - please refer sysFeatureProductFamily*"
	::= { sysTypeTableEntry 3 }

sysTypeSupportedMode  OBJECT-TYPE
	SYNTAX     DisplayString
	MAX-ACCESS read-only
	STATUS     current
	DESCRIPTION 
		"This parameter displays the supported modes of operations complying
		                 with the license."
	::= { sysTypeTableEntry 4 }

sysTypeSupportedFreqDomains  OBJECT-TYPE
	SYNTAX     DisplayString
	MAX-ACCESS read-only
	STATUS     current
	DESCRIPTION 
		"This parameter displays the supported frequency domains."
	::= { sysTypeTableEntry 5 }

sysTypeFreqDomain  OBJECT-TYPE
	SYNTAX     INTEGER {
		unitedStates5GHz (1),
		unitedStates5p8GHz (2),
		unitedStates2p4GHz (3),
		world5GHz (4),
		world4p9GHz (5),
		world2p4GHz (6),
		world2p3GHz (7),
		world2p5GHz (8),
		canada5GHz (9),
		wdeurope5p8GHz (10),
		wdeurope5p4GHz (11),
		wdeurope2p4GHz (12),
		russia5GHz (13),
		taiwan5GHz (14),
		wdunitedStates5GHz (15),
		canada5p8GHz (16),
		world6p4GHz (17),
		japan2p4GHz (18),
		japan4p9GHz (19),
		wduk5p8GHz (20),
		world5p9GHz (21),
		unitedStates5p3And5p8GHz (22),
		india5p8GHz (23),
		brazil5p4GHz (24),
		brazil5p8GHz (25),
		australia5p4GHz (26),
		australia5p8GHz (27),
		unitedStates4p9GHz (28),
		wdunitedStates4p9GHz (29),
		canada4p9GHz (30),
		wdjapan4p9GHz (31),
		wdlegacy5GHz (32),
		wdjapan5p6GHz (33),
		wdunitedStates5p8GHz (34),
		world5p8GHz (35),
		indonesia5p7GHz (36),
		minipcirussia6p4 (37),
		unitedStates5p2And5p8GHz (38),
		egypt5p8GHz (39),
		reserved (40),
		thailand2p4GHz (41),
		thailand5p2GHz (42),
		thailand5p6GHz (43),
		us4p9And5GHz (44),
		us5p3And5p4GHz (45),
		malaysia5p4GHz (46),
		malaysia5p8GHz (47),
		afghanistan5p8GHz (48),
		canada5p2GHz (49),
		canada5p3And5p4GHz (50),
		singapore5p4GHz (51),
		singapore5p8GHz (52),
		nigeria5p3GHz (53),
		nigeria5p4GHz (54),
		nigeria5p8GHz (55),
		nigeria5p3And5p8GHz (56),
		china5GHz (57)
	}
	MAX-ACCESS read-write
	STATUS     current
	DESCRIPTION 
		"This parameter is used to configure the frequency domain. The following
		                 list shows in detail: 
		                 - United States All: 5.3 + 5.4 with DFS and 5.8 without DFS
		                 - United States Adhoc: 5.8 without DFS only
		                 - United States 2.4 GHz
		                 - World All 
		                 - World 4.9 GHz (4.940 - 4.990 GHz) 
		                 - World 2.4 GHz (2.400 - 2.472 GHz)
		                 - World 2.3 GHz 
		                 - World 2.5 GHz 
		                 - Canada 5 GHz (5.250 - 5.350 & 5.470 - 5.600 & 5.650 - 5.725 GHz all bands with DFS) 
		                 - Russia 5 GHz (5.150 - 6.080 GHz without DFS)
		                 - Taiwan 5 GHz (5.500 - 5.700 with DFS & 5.725 - 5.825 GHz without DFS)
		                 - United State 5 GHz (5.250 - 5.350 & 5.470 - 5.725 GHz with DFS & 5.725 - 5.850 GHz without DFS)
		                         - Canada 5.8 GHz.
		                         - Russia Frequency Convertor.
		                         - Japan 2.4 GHz (2412 - 2472 MHz)  
		                         - Japan 4.9 GHz (4920 - 4980 MHz and 5040 - 5080 MHz).
		                         - World 5.9GHz
		                         - United States 5.3 and 5.8 GHz
		                         - India 5.8GHz
		                         - World 5.8GHz
		                         - Indonesia 5.7
		                         - MiniPci Russia 6.4GHz(It is Deprecated with World 6.4)
		                         - United States 5.2 and 5.8 GHz
		                         - Egypt 5.8 GHz
		                         - Thailand 2.4 GHz
		                         - Thailand 5.2 GHz
		                         - Thailand 5.6 GHz
		                         - US 4.9 and 5 GHz
		                         - United States 5.3 and 5.4 GHz
		                         - Malaysia 5.4 GHz 
		                         - Malaysia 5.8 GHz 
		                         - Afghanistan 5.8 GHz 
		                         - Canada 5.2 GHz 
		                         - Canada 5.3 and 5.4 GHz 
		                         - Singapore 5.4 GHz
		                         - Singapore 5.8 GHz 
		                         - Nigeria 5.3 GHz 
		                         - Nigeria 5.4 GHz 
		                         - Nigeria 5.8 GHz 
		                         - Nigeria 5.3 and 5.8 GHz 
		                         - China 5 GHz" 
	::= { sysTypeTableEntry 6 }

sysTypeActiveFreqDomain  OBJECT-TYPE
	SYNTAX     INTEGER {
		unitedStates5GHz (1),
		unitedStates5p8GHz (2),
		unitedStates2p4GHz (3),
		world5GHz (4),
		world4p9GHz (5),
		world2p4GHz (6),
		world2p3GHz (7),
		world2p5GHz (8),
		canada5GHz (9),
		wdeurope5p8GHz (10),
		wdeurope5p4GHz (11),
		wdeurope2p4GHz (12),
		russia5GHz (13),
		taiwan5GHz (14),
		wdunitedStates5GHz (15),
		canada5p8GHz (16),
		world6p4GHz (17),
		japan2p4GHz (18),
		japan4p9GHz (19),
		wduk5p8GHz (20),
		world5p9GHz (21),
		unitedStates5p3And5p8GHz (22),
		india5p8GHz (23),
		brazil5p4GHz (24),
		brazil5p8GHz (25),
		australia5p4GHz (26),
		australia5p8GHz (27),
		unitedStates4p9GHz (28),
		wdunitedStates4p9GHz (29),
		canada4p9GHz (30),
		wdjapan4p9GHz (31),
		wdlegacy5GHz (32),
		wdjapan5p6GHz (33),
		wdunitedStates5p8GHz (34),
		world5p8GHz (35),
		indonesia5p7GHz (36),
		minipcirussia6p4 (37),
		unitedStates5p2And5p8GHz (38),
		egypt5p8GHz (39),
		reserved (40),
		thailand2p4GHz (41),
		thailand5p2GHz (42),
		thailand5p6GHz (43),
		us4p9And5GHz (44),
		us5p3And5p4GHz (45),
		malaysia5p4GHz (46),
		malaysia5p8GHz (47),
		afghanistan5p8GHz (48),
		canada5p2GHz (49),
		canada5p3And5p4GHz (50),
		singapore5p4GHz (51),
		singapore5p8GHz (52),
		nigeria5p3GHz (53),
		nigeria5p4GHz (54),
		nigeria5p8GHz (55),
		nigeria5p3And5p8GHz (56),
		china5GHz (57)
	}
	MAX-ACCESS read-only
	STATUS     current
	DESCRIPTION 
		"This parameter shows the active frequency domain. The following
		                 list shows in detail:
		                 - United States All: 5.3 + 5.4 with DFS and 5.8 without DFS
		                 - United States Adhoc: 5.8 without DFS only
		                 - United States 2.4 GHz
		                 - World All
		                 - World 4.9 GHz (4.940 - 4.990 GHz)
		                 - World 2.4 GHz (2.400 - 2.472 GHz)
		                 - World 2.3 GHz
		                 - World 2.5 GHz
		                 - Canada 5 GHz (5.250 - 5.350 & 5.470 - 5.600 & 5.650 - 5.725 GHz all bands with DFS)
		                 - Europe 5.8 GHz (5.725 - 5.850 GHz with DFS)
		                 - Europe 5.4 GHz (5.470 - 5.600 & 5.650 - 5.725 GHz  both with DFS)
		                 - Europe 2.4 GHz (2.400 - 2.4825 GHz)
		                 - Russia 5 GHz (5.150 - 6.080 GHz without DFS)
		                 - Taiwan 5 GHz (5.500 - 5.700 with DFS & 5.725 - 5.825 GHz without DFS)
		                 - United State 5 GHz (5.250 - 5.350 & 5.470 - 5.725 GHz with DFS & 5.725 - 5.850 GHz without DFS)
		                         - Canada 5.8 GHz.
		                         - Russia Frequency Convertor
		                         - Japan 2.4 GHz (2412 - 2472 MHz)  
		                         - Japan 4.9 GHz (4920 - 4980 MHz and 5040 - 5080 MHz).
		                         - UK 5.8 GHz (5725 - 5795 MHz and 5825 - 5850 MHz)
		                         - World 5.9GHz
		                         - United States 5.3 and 5.8 GHz
		                         - India 5.8GHz
		                         - Japan 5.6GHz
		                         - WD United States 5.8 GHz
		                         - World 5.8 GHz
		                         - Indonesia 5.7 GHz
		 - MiniPci Russia 6.4GHz(It is Deprecated with World 6.4).
		                         - United States 5.2 and 5.8 GHz
		                         - Egypt 5.8 GHz
		                         - Thailand 2.4 GHz
		                         - Thailand 5.2 GHz
		                         - Thailand 5.6 GHz
		                         - US 4.9 and 5 GHz
		                         - United States 5.3 and 5.4 GHz
		                         - Malaysia 5.4 GHz 
		                         - Malaysia 5.8 GHz 
		                         - Afghanistan 5.8 GHz 
		                         - Canada 5.2 GHz 
		                         - Canada 5.3 and 5.4 GHz 
		                         - Singapore 5.4 GHz
		                         - Singapore 5.8 GHz 
		                         - Nigeria 5.3 GHz 
		                         - Nigeria 5.4 GHz 
		                         - Nigeria 5.8 GHz 
		                         - Nigeria 5.3 and 5.8 GHz 
		                         - China 5 GHz"
	::= { sysTypeTableEntry 7 }

sysConfFreqFilterLowerEdge  OBJECT-TYPE
	SYNTAX     Unsigned32 (0..10000)
	MAX-ACCESS read-write
	STATUS     current
	DESCRIPTION 
		"TBD"
	DEFVAL  { 0 }
	::= { sysTypeTableEntry 8 }

sysConfFreqFilterUpperEdge  OBJECT-TYPE
	SYNTAX     Unsigned32 (0..10000)
	MAX-ACCESS read-write
	STATUS     current
	DESCRIPTION 
		"TBD"
	DEFVAL  { 0 }
	::= { sysTypeTableEntry 9 }

-- System Network mode

sysNetworkMode  OBJECT-TYPE
	SYNTAX     INTEGER {
		bridge (1),
		route (2)
	}
	MAX-ACCESS read-write
	STATUS     current
	DESCRIPTION 
		" This parameter is used to configure the network mode of the
		                  device."
	DEFVAL  { bridge }
	::= { sysConf 2 }

-- Active Network Mode

sysActiveNetworkMode  OBJECT-TYPE
	SYNTAX     INTEGER {
		bridge (1),
		route (2)
	}
	MAX-ACCESS read-only
	STATUS     current
	DESCRIPTION 
		" This parameter is shows the network mode of the
		                  device. This can be configured in the sysNetworkMode."
	::= { sysConf 3 }

-- System Country Code

sysConfCountryCode  OBJECT-TYPE
	SYNTAX     DisplayString (SIZE(0..255))
	MAX-ACCESS read-write
	STATUS     current
	DESCRIPTION 
		"This attribute identifies the country in which the station is  
		    operating to set the frequency band. The first two octets of this 
		                    string is the two character country code as described in document 
		                    ISO/IEC 3166-1.
		 
		                    This object is not supported for the current products, please refer 
		                    sysTypeFreqDomain for configuring the Frequency band.
		                    
		                    Below is the list of mapping of country codes to country names.
		            A5 - ALL5GHz 
		            AL - ALBANIA 
		            DZ - ALGERIA 
		            AR - ARGENTINA 
		            AM - ARMENIA 
		            AU - AUSTRALIA 
		            AT - AUSTRIA 
		            AZ - AZERBAIJAN 
		            BH - BAHRAIN 
		            BY - BELARUS 
		            BE - BELGIUM 
		            BZ - BELIZE 
		            BO - BOLIVIA 
		            BR - BRAZIL 
		            BN - BRUNEI DARUSSALAM 
		            BG - BULGARIA 
		            CA - CANADA 
		            CL - CHILE 
		            CN - CHINA 
		            CO - COLOMBIA 
		            CR - COSTA RICA 
		            HR - CROATIA 
		            CY - CYPRUS 
		            CZ - CZECH REPUBLIC 
		            DK - DENMARK 
		            DO - DOMINICAN REPUBLIC 
		            EC - ECUADOR 
		            EG - EGYPT 
		            EE - ESTONIA 
		            EU - EUROPEAN UNION
		            FI - FINLAND 
		            FR - FRANCE 
		            GE - GEORGIA 
		            DE - GERMANY 
		            GR - GREECE 
		            GT - GUATEMALA 
		            HK - HONG KONG 
		            HU - HUNGARY 
		            IS - ICELAND 
		            IN - INDIA 
		            ID - INDONESIA 
		            IR - IRAN 
		            IE - IRELAND 
		            I1 - IRELAND - 5.8GHz 
		            IL - ISRAEL 
		            IT - ITALY 
		            JP - JAPAN 
		            J2 - JAPAN2
		            JM - JAMAICA 
		            JO - JORDAN 
		            KZ - KAZAKHSTAN 
		            KP - NORTH KOREA 
		            KR - KOREA REPUBLIC 
		            K2 - KOREA REPUBLIC2 
		            KW - KUWAIT 
		            LV - LATVIA 
		            LB - LEBANON 
		            LI - LIECHTENSTEIN 
		            LT - LITHUANIA 
		            LU - LUXEMBOURG 
		            MO - MACAU 
		            MK - MACEDONIA 
		            MT - MALTA 
		            MY - MALAYSIA 
		            MX - MEXICO 
		            MC - MONACO 
		            MA - MOROCCO 
		            NL - NETHERLANDS 
		            NZ - NEW ZEALAND 
		            NO - NORWAY 
		            OM - OMAN 
		            PK - PAKISTAN 
		            PA - PANAMA 
		            PE - PERU 
		            PH - PHILIPPINES 
		            PL - POLAND 
		            PT - PORTUGAL 
		            PR - PUERTO RICO 
		            QA - QATAR 
		            RO - ROMANIA 
		            RU - RUSSIA 
		            SA - SAUDI ARABIA 
		            CS - SERBIA & MONTENEGRO
		            SG - SINGAPORE 
		            SK - SLOVAK REPUBLIC 
		            SI - SLOVENIA 
		            ZA - SOUTH AFRICA 
		            ES - SPAIN 
		            SE - SWEDEN 
		            CH - SWITZERLAND 
		            SY - SYRIA 
		            TW - TAIWAN 
		            TH - THAILAND 
		            TR - TURKEY 
		            UA - UKRAINE 
		            AE - UNITED ARAB EMIRATES 
		            GB - UNITED KINGDOM 
		            G1 - UNITED KINGDOM - 5.8GHz 
		            US - UNITED STATES 
		            UW - UNITED STATES - World 
		            U1 - UNITED STATES - DFS 
		            UY - URUGUAY 
		            VE - VENEZUELA 
		            VN - VIETNAM"
	::= { sysConf 4 }

sysMaxMTUSupported  OBJECT-TYPE
	SYNTAX     Unsigned32
	MAX-ACCESS read-only
	STATUS     current
	DESCRIPTION 
		"TBD"
	::= { sysConf 5 }

sysConfMaxMTUSupport  OBJECT-TYPE
	SYNTAX     Unsigned32 (64..2048)
	MAX-ACCESS read-write
	STATUS     current
	DESCRIPTION 
		"TBD"
	DEFVAL  { 1600 }
	::= { sysConf 6 }

sysLEDStackStatus  OBJECT-TYPE
	SYNTAX     INTEGER {
		disable (1),
		rssi (2),
		sync (3)
	}
	MAX-ACCESS read-write
	STATUS     current
	DESCRIPTION 
		"This parameter is used to configure LED Stack Status."
	DEFVAL  { rssi }
	::= { sysLEDStack 1 }

sysLEDStackSUMACAddr  OBJECT-TYPE
	SYNTAX     MacAddress
	MAX-ACCESS read-write
	STATUS     current
	DESCRIPTION 
		"This parameter is used to configure MAC Address of SU to monitor the RSSI."
	::= { sysLEDStack 2 }

-- Standalone Mode - Device is managed locally.
-- Controller Mode    - Device is managed through Controller.

sysMgmtMode  OBJECT-TYPE
	SYNTAX     INTEGER {
		standaloneMode (1),
		controllerMode (2)
	}
	MAX-ACCESS read-write
	STATUS     current
	DESCRIPTION 
		"Standalone Mode - Device is managed locally.
		Controller Mode    - Device is managed through Controller."
	DEFVAL  { standaloneMode }
	::= { sysConf 8 }

-- All possible status for Device association with Controller.
-- 
-- Discover Request	       - Discovering Controller.
-- Key Request	       - Discovering Controller using caching.	
-- Auth Request	       - Controller Authenticated.
-- Key Response	       - Controller Authenticated using caching.
-- Auth Response               - Waiting for Controller to authenticate Device
-- Acknowledgement	       - Device Associated with Controller.
-- Controller Auth Fail	       - Not an authenticated Controller.
-- Device Auth Fail	       - Device authentication fail on Controller.
-- Controller Mode disable  - Controller mode disable.
-- 

sysCtrlAssociationState  OBJECT-TYPE
	SYNTAX     INTEGER {
		discoverRequest (1),
		keyRequest (2),
		authRequest (3),
		keyResponse (4),
		authResponse (5),
		acknowledgement (6),
		controllerAuthFail (7),
		deviceAuthFail (8),
		disable (9)
	}
	MAX-ACCESS read-only
	STATUS     current
	DESCRIPTION 
		"All possible status for Device association with Controller.
		
		 Discover Request	       - Discovering Controller.
		 Key Request	       - Discovering Controller using caching.	
		 Auth Request	       - Controller Authenticated.
		 Key Response	       - Controller Authenticated using caching.
		 Auth Response               - Waiting for Controller to authenticate Device
		 Acknowledgement	       - Device Associated with Controller.
		 Controller Auth Fail	       - Not an authenticated Controller.
		 Device Auth Fail	       - Device authentication fail on Controller.
		 Controller Mode disable  - Controller mode disable.
		"
	DEFVAL  { disable }
	::= { sysConf 9 }

sysIsPreConfigured  OBJECT-TYPE
	SYNTAX     Unsigned32 (0..1)
	MAX-ACCESS read-write
	STATUS     current
	DESCRIPTION 
		"This parameter represents whether the device is having configuration or not. 
		        0 - Factory Default Configuration 
		        1 - Device is Pre-Configured."
		
	DEFVAL  { 0 }
	::= { sysConf 10 }

-- ======================================================================================
-- Definition of the IGMP Group objects
-- ======================================================================================       
-- IGMP Group objects
-- Global IGMP Snooping Flag

igmpSnoopingGlobalStatus  OBJECT-TYPE
	SYNTAX     INTEGER {
		enable (1),
		disable (2)
	}
	MAX-ACCESS read-write
	STATUS     current
	DESCRIPTION 
		"This parameter is used to enable/disable the IGMP snooping. Only passive
		                  snooping is supported. This feature is supported only in bridge mode."
	::= { igmp 1 }

-- IGMP Membership Aging Timer 

igmpMembershipAgingTimer  OBJECT-TYPE
	SYNTAX     Unsigned32
	MAX-ACCESS read-write
	STATUS     current
	DESCRIPTION 
		"This parameter represents the time after which the IGMP multicast group
		                 age-outs/elapses."
	::= { igmp 2 }

-- IGMP Router Port Aging Timer

igmpRouterPortAgingTimer  OBJECT-TYPE
	SYNTAX     Unsigned32
	MAX-ACCESS read-write
	STATUS     current
	DESCRIPTION 
		"This parameter represents the time after which the IGMP router port 
		                 age-outs/elapses."
	::= { igmp 3 }

-- IGMP Forced Flood

igmpForcedFlood  OBJECT-TYPE
	SYNTAX     INTEGER {
		yes (1),
		no (2)
	}
	MAX-ACCESS read-write
	STATUS     current
	DESCRIPTION 
		"If this paramter is set with Yes, all unregistered  multicast traffic
		                 and membership reports will be flooded to all ports."
	::= { igmp 4 }

-- ======================================================================================
-- Definition of the System Group objects
-- ======================================================================================	
-- System Country Code

sysCountryCode  OBJECT-TYPE
	SYNTAX     DisplayString (SIZE(0..255))
	MAX-ACCESS read-write
	STATUS     deprecated
	DESCRIPTION 
		"This attribute identifies the country in which the station is  
		    operating. The first two octets of this string is the two character  
		    country code as described in document ISO/IEC 3166-1.  Below is the  
		    list of mapping of country codes to country names. This object is 
		                    deprecated and please use sysConfCountryCode to set the country code.
		            AL - ALBANIA 
		            DZ - ALGERIA 
		            AR - ARGENTINA 
		            AM - ARMENIA 
		            AU - AUSTRALIA 
		            AT - AUSTRIA 
		            AZ - AZERBAIJAN 
		            BH - BAHRAIN 
		            BY - BELARUS 
		            BE - BELGIUM 
		            BZ - BELIZE 
		            BO - BOLIVIA 
		            BR - BRAZIL 
		            BN - BRUNEI DARUSSALAM 
		            BG - BULGARIA 
		            CA - CANADA 
		            CL - CHILE 
		            CN - CHINA 
		            CO - COLOMBIA 
		            CR - COSTA RICA 
		            HR - CROATIA 
		            CY - CYPRUS 
		            CZ - CZECH REPUBLIC 
		            DK - DENMARK 
		            DO - DOMINICAN REPUBLIC 
		            EC - ECUADOR 
		            EG - EGYPT 
		            EE - ESTONIA 
		            EU - EUROPEAN UNION
		            FI - FINLAND 
		            FR - FRANCE 
		            GE - GEORGIA 
		            DE - GERMANY 
		            GR - GREECE 
		            GT - GUATEMALA 
		            HK - HONG KONG 
		            HU - HUNGARY 
		            IS - ICELAND 
		            IN - INDIA 
		            ID - INDONESIA 
		            IR - IRAN 
		            IE - IRELAND 
		            I1 - IRELAND - 5.8GHz 
		            IL - ISRAEL 
		            IT - ITALY 
		            JP - JAPAN 
		            J2 - JAPAN2
		            JM - JAMAICA 
		            JO - JORDAN 
		            KZ - KAZAKHSTAN 
		            KP - NORTH KOREA 
		            KR - KOREA REPUBLIC 
		            K2 - KOREA REPUBLIC2 
		            KW - KUWAIT 
		            LV - LATVIA 
		            LB - LEBANON 
		            LI - LIECHTENSTEIN 
		            LT - LITHUANIA 
		            LU - LUXEMBOURG 
		            MO - MACAU 
		            MK - MACEDONIA 
		            MT - MALTA 
		            MY - MALAYSIA 
		            MX - MEXICO 
		            MC - MONACO 
		            MA - MOROCCO 
		            NL - NETHERLANDS 
		            NZ - NEW ZEALAND 
		            NO - NORWAY 
		            OM - OMAN 
		            PK - PAKISTAN 
		            PA - PANAMA 
		            PE - PERU 
		            PH - PHILIPPINES 
		            PL - POLAND 
		            PT - PORTUGAL 
		            PR - PUERTO RICO 
		            QA - QATAR 
		            RO - ROMANIA 
		            RU - RUSSIA 
		            SA - SAUDI ARABIA 
		            CS - SERBIA & MONTENEGRO
		            SG - SINGAPORE 
		            SK - SLOVAK REPUBLIC 
		            SI - SLOVENIA 
		            ZA - SOUTH AFRICA 
		            ES - SPAIN 
		            SE - SWEDEN 
		            CH - SWITZERLAND 
		            SY - SYRIA 
		            TW - TAIWAN 
		            TH - THAILAND 
		            TR - TURKEY 
		            UA - UKRAINE 
		            AE - UNITED ARAB EMIRATES 
		            GB - UNITED KINGDOM 
		            G1 - UNITED KINGDOM - 5.8GHz 
		            US - UNITED STATES 
		            UW - UNITED STATES - World 
		            U1 - UNITED STATES - DFS 
		            UY - URUGUAY 
		            VE - VENEZUELA 
		            VN - VIETNAM"
	::= { sys 1 }

-- ======================================================================================
-- Definition of the sysInvMgmt Subgroup objects
-- ======================================================================================	
-- System Inventory Mgmt Component Table

sysInvMgmtComponentTable  OBJECT-TYPE
	SYNTAX SEQUENCE OF SysInvMgmtComponentTableEntry
	MAX-ACCESS not-accessible
	STATUS     current
	DESCRIPTION 
		"This table holds the system's inventory management component features."
	::= { sysInvMgmt 1 }

sysInvMgmtComponentTableEntry  OBJECT-TYPE
	SYNTAX 	SysInvMgmtComponentTableEntry
	MAX-ACCESS not-accessible
	STATUS     current
	DESCRIPTION 
		"This parameter represents the entry for the sysInvmgmtComponentTable"
	INDEX { sysInvMgmtCompTableIndex }
	::= { sysInvMgmtComponentTable 1 }

SysInvMgmtComponentTableEntry ::= SEQUENCE {
	sysInvMgmtCompTableIndex
		Unsigned32,
	sysInvMgmtCompSerialNumber
		DisplayString,
	sysInvMgmtCompName
		DisplayString,
	sysInvMgmtCompId
		Unsigned32,
	sysInvMgmtCompVariant
		Unsigned32,
	sysInvMgmtCompReleaseVersion
		Unsigned32,
	sysInvMgmtCompMajorVersion
		Unsigned32,
	sysInvMgmtCompMinorVersion
		Unsigned32
}

sysInvMgmtCompTableIndex  OBJECT-TYPE
	SYNTAX     Unsigned32
	MAX-ACCESS read-only
	STATUS     current
	DESCRIPTION 
		"This parameter represents the index for sysInvMgmtCompTable."
	::= { sysInvMgmtComponentTableEntry 1 }

sysInvMgmtCompSerialNumber  OBJECT-TYPE
	SYNTAX     DisplayString
	MAX-ACCESS read-only
	STATUS     current
	DESCRIPTION 
		"This parameter identifies the system component serial number"
	::= { sysInvMgmtComponentTableEntry 2 }

sysInvMgmtCompName  OBJECT-TYPE
	SYNTAX     DisplayString
	MAX-ACCESS read-only
	STATUS     current
	DESCRIPTION 
		"This parameter identifies the system component name."
	::= { sysInvMgmtComponentTableEntry 3 }

sysInvMgmtCompId  OBJECT-TYPE
	SYNTAX     Unsigned32
	MAX-ACCESS read-only
	STATUS     current
	DESCRIPTION 
		"This parameter shows the identifier for the component."
	::= { sysInvMgmtComponentTableEntry 4 }

sysInvMgmtCompVariant  OBJECT-TYPE
	SYNTAX     Unsigned32
	MAX-ACCESS read-only
	STATUS     current
	DESCRIPTION 
		"This parameter identifies the system component variant number."
	::= { sysInvMgmtComponentTableEntry 5 }

sysInvMgmtCompReleaseVersion  OBJECT-TYPE
	SYNTAX     Unsigned32
	MAX-ACCESS read-only
	STATUS     current
	DESCRIPTION 
		"This parameter identifies the system component release version number."
	::= { sysInvMgmtComponentTableEntry 6 }

sysInvMgmtCompMajorVersion  OBJECT-TYPE
	SYNTAX     Unsigned32
	MAX-ACCESS read-only
	STATUS     current
	DESCRIPTION 
		"This parameter identifies the system component major version number."
	::= { sysInvMgmtComponentTableEntry 7 }

sysInvMgmtCompMinorVersion  OBJECT-TYPE
	SYNTAX     Unsigned32
	MAX-ACCESS read-only
	STATUS     current
	DESCRIPTION 
		"This parameters identifies the system component minor version number."
	::= { sysInvMgmtComponentTableEntry 8 }

-- System Inventory Management Security Identifier

sysInvMgmtSecurityID  OBJECT-TYPE
	SYNTAX     DisplayString
	MAX-ACCESS read-only
	STATUS     current
	DESCRIPTION 
		" This parameter represents the system's Security ID."
	::= { sysInvMgmt 2 }

-- Daughter Card Availability

sysInvMgmtDaughterCardAvailability  OBJECT-TYPE
	SYNTAX     INTEGER {
		yes (1),
		no (2)
	}
	MAX-ACCESS read-only
	STATUS     current
	DESCRIPTION 
		"This parameter shows the availability of the daughter card."
	::= { sysInvMgmt 3 }

-- ======================================================================================
-- Definition of the sysFeature Subgroup objects
-- ======================================================================================	
-- System Feature Control Identifier

sysFeatureCtrlID  OBJECT-TYPE
	SYNTAX     Unsigned32
	MAX-ACCESS read-only
	STATUS     current
	DESCRIPTION 
		"This parameter is used to represent the control ID for the system feature. "
	::= { sysFeature 1 }

-- Number of radios present

sysFeatureNumRadios  OBJECT-TYPE
	SYNTAX     Unsigned32
	MAX-ACCESS read-only
	STATUS     current
	DESCRIPTION 
		"This parameter shows the number of radios supported. This is based on the license file. "
	::= { sysFeature 2 }

-- Frequency band used

sysFeatureFreqBand  OBJECT-TYPE
	SYNTAX     DisplayString
	MAX-ACCESS read-only
	STATUS     current
	DESCRIPTION 
		"This parameter shows the supported frequency bands. This is based on the license file."
	::= { sysFeature 3 }

-- Out Bandwidth

sysFeatureOutBandwidth  OBJECT-TYPE
	SYNTAX     Unsigned32
	MAX-ACCESS read-only
	STATUS     current
	DESCRIPTION 
		"This parameter represents the outward bandwidth in multiples of 1Mbps. This is based on the license file"
	::= { sysFeature 4 }

-- In Bandwidth

sysFeatureInBandwidth  OBJECT-TYPE
	SYNTAX     Unsigned32
	MAX-ACCESS read-only
	STATUS     current
	DESCRIPTION 
		"This parameter represents the inward bandwidth in multiples of 1Mbps. This is based on the license file."
	::= { sysFeature 5 }

-- Operational Mode

sysFeatureOpMode  OBJECT-TYPE
	SYNTAX     DisplayString
	MAX-ACCESS read-only
	STATUS     current
	DESCRIPTION 
		"This parameter represents the current operational mode of the device. This is based on the license file."
	::= { sysFeature 6 }

-- System License Feature Set Table

sysLicFeatureTable  OBJECT-TYPE
	SYNTAX SEQUENCE OF SysLicFeatureTableEntry
	MAX-ACCESS not-accessible
	STATUS     current
	DESCRIPTION 
		"This table contains a list of features that the current image supports
		                 and indicates if this feature is licensed or not. Each row represents a 
		                 supported feature. Supported indicates if the current image supports the image 
		                 while licensed indicates that a license is available to use this feature.
		                 Based on the license information in this table, some MIB groups/subgroups/tables
		                 are enabled or disabled."
	::= { sysFeature 7 }

sysLicFeatureTableEntry  OBJECT-TYPE
	SYNTAX 	SysLicFeatureTableEntry
	MAX-ACCESS not-accessible
	STATUS     current
	DESCRIPTION 
		"This table parameter represents the entry for the sysLicFeatureTable. This
		                  table can hold a maximum of 50 entries."
	INDEX { sysLicFeatureTableIndex }
	::= { sysLicFeatureTable 1 }

SysLicFeatureTableEntry ::= SEQUENCE {
	sysLicFeatureTableIndex
		Unsigned32,
	sysLicFeatureType
		Unsigned32,
	sysLicFeatureValue
		Unsigned32
}

sysLicFeatureTableIndex  OBJECT-TYPE
	SYNTAX     Unsigned32
	MAX-ACCESS read-only
	STATUS     current
	DESCRIPTION 
		"This parameter represents the index for the sysLicFeatureTable."
	::= { sysLicFeatureTableEntry 1 }

sysLicFeatureType  OBJECT-TYPE
	SYNTAX     Unsigned32
	MAX-ACCESS read-only
	STATUS     current
	DESCRIPTION 
		"This parameter represents the feature type and shows the code of the feature."
	::= { sysLicFeatureTableEntry 2 }

sysLicFeatureValue  OBJECT-TYPE
	SYNTAX     Unsigned32
	MAX-ACCESS read-only
	STATUS     current
	DESCRIPTION 
		"This parameter represents feature value i.e., enabled or disabled."
	::= { sysLicFeatureTableEntry 3 }

-- Cumulative Bandwidth 

sysFeatureCumulativeBandwidth  OBJECT-TYPE
	SYNTAX     Unsigned32
	MAX-ACCESS read-only
	STATUS     current
	DESCRIPTION 
		"This parameter represents the cumulative bandwidth of the device. This is based on the license file."
	::= { sysFeature 8 }

-- Number of Ethernet interfaces

sysFeatureNumEtherIf  OBJECT-TYPE
	SYNTAX     Unsigned32
	MAX-ACCESS read-only
	STATUS     current
	DESCRIPTION 
		"This parameter represents the number of ethernet interfaces supported. This is based on the license file."
	::= { sysFeature 9 }

-- Feature Bit Map

sysFeatureBitmap  OBJECT-TYPE
	SYNTAX     Unsigned32
	MAX-ACCESS read-only
	STATUS     current
	DESCRIPTION 
		"This parameter represents the bit map for the features enabled/disabled. 
		                 The value for this parameter is interpreted as a bitfield and the respective
		                 modules are shown below: 
		                 
		             BRIDGE_MODE_ONLY       = 0,
		                 WORP                   = 1,
		                 Intra Cell Blocking    = 2,
		                 Intra BSS Blocking     = 3,
		                 VLAN                   = 4,
		                 STATIC_ROUTING         = 5,
		                 NAT                    = 6,
		                 FILTERING              = 7, 
		                         System MTU             = 8,
		                         MAC ACL                = 9,
		                         Radius                 = 10,
		                         IGMP                   = 11,
		                         MESH                   = 12,
		                         Ethernet Auto Shutdown = 13,
		                         PPoE                   = 14,
		                         Device conversion to SU= 15,
		                         Channel Offset         = 16,
		                         Radius VLAN            = 17,
		                         QB to SU conversion    = 18,
		                         Spectrum Analyzer      = 19,
		                         Roaming                = 20,
		                         IPV6                   = 21,
		                         Sync                   = 22, 
		                         Controller             = 23, 
		                         DFS FCC LTV            = 24. This is based on the license file."
	::= { sysFeature 10 }

-- Max. Number of Satellites Allowed

sysFeatureNumOfSatellitesAllowed  OBJECT-TYPE
	SYNTAX     Unsigned32
	MAX-ACCESS read-only
	STATUS     current
	DESCRIPTION 
		"This parameter represents the max number of satellites supported. This is based on the license file."
	::= { sysFeature 11 }

-- Product Family

sysFeatureProductFamily  OBJECT-TYPE
	SYNTAX     INTEGER {
		tsunamiMP (1),
		orinocoAP (2),
		tsunamiQuickBridge (3)
	}
	MAX-ACCESS read-only
	STATUS     current
	DESCRIPTION 
		"This parameter represents the product family. This is based on the license file."
	::= { sysFeature 12 }

-- Product Class

sysFeatureProductClass  OBJECT-TYPE
	SYNTAX     INTEGER {
		indoor (0),
		outdoor (1)
	}
	MAX-ACCESS read-only
	STATUS     current
	DESCRIPTION 
		"This parameter represents the product class. This is based on the license file."
	::= { sysFeature 13 }

-- License file radio information table

sysLicRadioInfoTable  OBJECT-TYPE
	SYNTAX SEQUENCE OF SysLicRadioInfoTableEntry
	MAX-ACCESS not-accessible
	STATUS     current
	DESCRIPTION 
		"This table holds the license file parameters for the radio(s)."
	::= { sysFeature 14 }

sysLicRadioInfoTableEntry  OBJECT-TYPE
	SYNTAX 	SysLicRadioInfoTableEntry
	MAX-ACCESS not-accessible
	STATUS     current
	DESCRIPTION 
		"This table parameter represents the entry for the sysLicRadioInfoTable."
	INDEX { sysLicRadioInfoTableIndex }
	::= { sysLicRadioInfoTable 1 }

SysLicRadioInfoTableEntry ::= SEQUENCE {
	sysLicRadioInfoTableIndex
		Unsigned32,
	sysLicRadioCompID
		Unsigned32,
	sysLicRadiovariantID
		Unsigned32,
	sysLicRadioAntennaType
		INTEGER,
	sysLicRadioAntennaMimoType
		INTEGER
}

sysLicRadioInfoTableIndex  OBJECT-TYPE
	SYNTAX     Unsigned32
	MAX-ACCESS read-only
	STATUS     current
	DESCRIPTION 
		"This parameter represents the index for the sysLicRadioInfoTable."
	::= { sysLicRadioInfoTableEntry 1 }

sysLicRadioCompID  OBJECT-TYPE
	SYNTAX     Unsigned32
	MAX-ACCESS read-only
	STATUS     current
	DESCRIPTION 
		"This parameter represents the component ID for the radio(s)."
	::= { sysLicRadioInfoTableEntry 2 }

sysLicRadiovariantID  OBJECT-TYPE
	SYNTAX     Unsigned32
	MAX-ACCESS read-only
	STATUS     current
	DESCRIPTION 
		"This parameter represents the variant ID for the radio(s)."
	::= { sysLicRadioInfoTableEntry 3 }

sysLicRadioAntennaType  OBJECT-TYPE
	SYNTAX     INTEGER {
		invalid (0),
		connectorized (1),
		integrated (2)
	}
	MAX-ACCESS read-only
	STATUS     current
	DESCRIPTION 
		"This parameter represents the Antenna type supported for the radio(s)."
	::= { sysLicRadioInfoTableEntry 4 }

sysLicRadioAntennaMimoType  OBJECT-TYPE
	SYNTAX     INTEGER {
		invalid (0),
		oneCrossOneAntenna (1),
		twoCrossTwoAntenna (2),
		threeCrossThreeAntenna (3)
	}
	MAX-ACCESS read-only
	STATUS     current
	DESCRIPTION 
		"This parameter represents the Antenna MIMO type for the radio(s)."
	::= { sysLicRadioInfoTableEntry 5 }

sysFeatureDefaultPswdsBitmap  OBJECT-TYPE
	SYNTAX     Unsigned32
	MAX-ACCESS read-only
	STATUS     current
	DESCRIPTION 
    "This parameter represents the bit map to indicate default passwords
    The value for this parameter is interpreted as a bitfield and the respective
    modules are shown below:
        HTTP ADMIN PASSWORD       0
        HTTP MONITOR PASSWORD     1
        TELNET ADMIN PASSWORD     2
        TELNET MONITOR PASSWORD   3
        SNMP READ PASSWORD        4
        SNMP READ WRITE PASSWORD  5
        SNMP AUTH PASSWORD        6
        SNMP PRIV PASSWORD        7
    "
	::= { sysFeature 15 }

-- ======================================================================================
-- Definition of the sysMgmt Subgroup objects
-- ======================================================================================	
-- System Mgmt Config Change Count 

sysMgmtCfgChangeCnt  OBJECT-TYPE
	SYNTAX     Counter32
	MAX-ACCESS read-only
	STATUS     current
	DESCRIPTION 
		"This parameter represents the number of successful commits that has taken 
		 place since the system was rebooted last."
	::= { sysMgmt 1 }

-- System Mgmt Config Commit

sysMgmtCfgCommit  OBJECT-TYPE
	SYNTAX     Unsigned32
	MAX-ACCESS read-write
	STATUS     current
	DESCRIPTION 
		" This parameter is used to apply the changed configurations to the device.
		                  Always this should be SET with value '1' or '2'. 
                          1 - Commit, 2 - Temporary Commit
                          The values available on GET or
		                  the read values are defined as follows:
		                  200     : Commit Successful 
		                  201     : Commit Successful and reboot the device.
		                  
		                  Please check the object sysMgmtCfgErrorMsg for Commit status and other 
		                  information on errors.                  
		                  
		                  P.S: Usual commit operation needs atleast 3 seconds and changes in wireless 
		                        parameters needs upto 60 seconds time interval before sending the response."
	::= { sysMgmt 2 }

-- System Mgmt Config Restore

sysMgmtCfgRestore  OBJECT-TYPE
	SYNTAX     INTEGER {
		yes (1),
		no (2)
	}
	MAX-ACCESS read-write
	STATUS     current
	DESCRIPTION 
		"This parameter is used to restore the device to last working configuration"
	::= { sysMgmt 3 }

-- System mgmt Config Error Message

sysMgmtCfgErrorMsg  OBJECT-TYPE
	SYNTAX     DisplayString
	MAX-ACCESS read-only
	STATUS     current
	DESCRIPTION 
		" This parameter displays the latest error message occured in configuration."
	::= { sysMgmt 4 }

-- System mgmt Reboot

sysMgmtReboot  OBJECT-TYPE
	SYNTAX     INTEGER {
		yes (1),
		no (2)
	}
	MAX-ACCESS read-write
	STATUS     current
	DESCRIPTION 
		"This parameter is used to reboot device. Select 1 to reboot."
	::= { sysMgmt 5 }

sysMgmtFactoryReset  OBJECT-TYPE
	SYNTAX     INTEGER {
		yes (1),
		no (2)
	}
	MAX-ACCESS read-write
	STATUS     current
	DESCRIPTION 
		"This parameter is used to reset the device to factory settings."
	DEFVAL  { no }
	::= { sysMgmt 6 }

sysMgmtLoadTextConfig  OBJECT-TYPE
	SYNTAX     INTEGER {
		yes (1),
		no (2)
	}
	MAX-ACCESS read-write
	STATUS     current
	DESCRIPTION 
		"This parameter is used to load the configurations from the Text Based Configuration File."
	DEFVAL  { no }
	::= { sysMgmt 7 }

-- System mgmt command

sysMgmtCommand  OBJECT-TYPE
	SYNTAX     INTEGER {
		none (1),
		convertQBtoSU (2)
	}
	MAX-ACCESS read-write
	STATUS     current
	DESCRIPTION 
		"TBD"
	::= { sysMgmt 8 }

-- System Mgmt Cfg Profile Exclude Parameters

sysMgmtCfgProfileExcludeParam  OBJECT-TYPE
	SYNTAX     Unsigned32
	MAX-ACCESS read-write
	STATUS     current
	DESCRIPTION 
		" This parameter shows the unique parameters to be excluded from configuration profile.
		  This is implemented as bitmap.By default 0 and 1 are enabled.
		  0     : System Information (name, coordinate, contact information...)
		  1     : IP configuration (static/dynamic, address, mask, gateway, DNS)
		  2     : Ethernet configuration (speed & duplex, admin status, auto shutdown)
		  3     : Wireless configuration (preferred channel, offset, antenna gain, channel bandwidth)"
	::= { sysMgmt 9 }

-- System Mgmt Cfg Profile Create

sysMgmtCfgProfileCreate  OBJECT-TYPE
	SYNTAX     Unsigned32
	MAX-ACCESS read-write
	STATUS     current
	DESCRIPTION 
		" This parameter is used to create the config profile file. Set 1 to create profile."
	::= { sysMgmt 10 }

-- System Mgmt Cfg Profile Apply

sysMgmtCfgProfileApply  OBJECT-TYPE
	SYNTAX     Unsigned32
	MAX-ACCESS read-write
	STATUS     current
	DESCRIPTION 
		" This parameter is used to apply the config profile on device. Set 1 to apply on device."
	::= { sysMgmt 11 }

-- System Mgmt Reboot Required

sysMgmtCfgRebootRequired  OBJECT-TYPE
	SYNTAX     Unsigned32
	MAX-ACCESS read-only
	STATUS     current
	DESCRIPTION 
		" This parameter shows if reboot is required to the device.
		                  1     : Rebbot is required
		                  0     : Reboot is not required."
	::= { sysMgmt 12 }

-- sysMgmtLanguage 

sysMgmtLanguage  OBJECT-TYPE
	SYNTAX     INTEGER {
		english (1),
		chinese (2),
		spanish (3),
		french (4)
	}
	MAX-ACCESS read-write
	STATUS     current
	DESCRIPTION 
		"This parameter is used to change the display language of the new web
		 1.English
		 2.Chinese
		 3.Spanish
		 4.French
		"
	DEFVAL  { english }
	::= { sysMgmt 13 }

-- sysMgmtActiveLanguage

sysMgmtActiveLanguage  OBJECT-TYPE
	SYNTAX     INTEGER {
		english (1),
		chinese (2),
		spanish (3),
		french (4)
	}
	MAX-ACCESS read-only
	STATUS     current
	DESCRIPTION 
		"This parameter is used to get the current active language displaying in the web 
		 1.English
		 2.Chinese
		 3.Spanish
		 4.French"
	DEFVAL  { english }
	::= { sysMgmt 14 }

sysMgmtProductFamily  OBJECT-TYPE
	SYNTAX     INTEGER {
		mp (1),
		qb (3)
	}
	MAX-ACCESS read-write
	STATUS     current
	DESCRIPTION 
		""
	::= { sysMgmt 15 }

-- ======================================================================================
-- Definition of the sysInfo Subgroup objects
-- ======================================================================================	
-- Contact email

sysContactEmail  OBJECT-TYPE
	SYNTAX     DisplayString (SIZE(6..32))
	MAX-ACCESS read-write
	STATUS     current
	DESCRIPTION 
		"This parameter is used to identify the email address of the 
		 contact person for a device. The length of the email address should be 
		 between 6 to 32"
	DEFVAL  { "name@Organization.com" }
	::= { sysInfo 1 }

-- Contact Phone Number

sysContactPhoneNumber  OBJECT-TYPE
	SYNTAX     DisplayString (SIZE(6..32))
	MAX-ACCESS read-write
	STATUS     current
	DESCRIPTION 
		" This parameter is used to identify the phone number of the
		  contact person for a device."
	DEFVAL  { " Contact-Phone-Number" }
	::= { sysInfo 2 }

-- Location

sysLocationName  OBJECT-TYPE
	SYNTAX     DisplayString (SIZE(0..255))
	MAX-ACCESS read-write
	STATUS     current
	DESCRIPTION 
		"This parameter is used to store the location of the system."
	::= { sysInfo 3 }

-- GPS Longitude

sysGPSLongitude  OBJECT-TYPE
	SYNTAX     DisplayString (SIZE(0..255))
	MAX-ACCESS read-write
	STATUS     current
	DESCRIPTION 
		" This parameter is used to represent Longitude."
	::= { sysInfo 4 }

-- GPS Latitude

sysGPSLatitude  OBJECT-TYPE
	SYNTAX     DisplayString (SIZE(0..255))
	MAX-ACCESS read-write
	STATUS     current
	DESCRIPTION 
		" This parameter is used to represent Latitude."
	::= { sysInfo 5 }

-- GPS Altitude

sysGPSAltitude  OBJECT-TYPE
	SYNTAX     DisplayString (SIZE(0..255))
	MAX-ACCESS read-write
	STATUS     current
	DESCRIPTION 
		"This parameter is used to display the elevation of an access point 
		 from a known level. "
	::= { sysInfo 6 }

-- Product Description

productDescr  OBJECT-TYPE
	SYNTAX     DisplayString
	MAX-ACCESS read-only
	STATUS     current
	DESCRIPTION 
		"A textual description of the entity.  This value
		                 should includes the full name and version
		                 identification of the system's hardware type,
		                 software operating-system, and networking
		                 software."
	::= { sysInfo 7 }

-- System Name

systemName  OBJECT-TYPE
	SYNTAX     DisplayString (SIZE(0..64))
	MAX-ACCESS read-write
	STATUS     current
	DESCRIPTION 
		"An administratively-assigned name for this managed node.  
		 By convention, this is the node's fully-qualified domain name."
	::= { sysInfo 8 }

-- This object will be mapped with standard MIB sysContact object.

systemContact  OBJECT-TYPE
	SYNTAX     DisplayString (SIZE(0..255))
	MAX-ACCESS read-write
	STATUS     current
	DESCRIPTION 
		"The textual identification of the contact person for this managed node, 
		together with information on how to contact this person."
	::= { sysInfo 9 }

-- ======================================================================================
-- Definition of the mgmtSnmp Group objects
-- ======================================================================================
-- SNMP Read Password

mgmtSnmpReadPassword  OBJECT-TYPE
	SYNTAX     Password
	MAX-ACCESS read-write
	STATUS     current
	DESCRIPTION 
		"This parameter is used for the SNMP password and represents the read-only
		 community name used in the SNMP protocol.It is used for reading objects 
		 from the SNMP agent. The password should be treated as write-only and would
		 be returned as asterisks. User is not allowed to set since it is same as 
		                 mgmtSnmpReadWritePassword"
	::= { mgmtSnmp 1 }

-- SNMP Read/Write Password

mgmtSnmpReadWritePassword  OBJECT-TYPE
	SYNTAX     Password
	MAX-ACCESS read-write
	STATUS     current
	DESCRIPTION 
		"This parameter is used to represent the read-write community name used 
		 in the SNMP protocol. This parameter is used for reading and writing objects 
		 to the SNMP agent. This parameter should be treated as write-only and 
		  returned as asterisks.
		 "
	::= { mgmtSnmp 2 }

-- SNMP Access Table

mgmtSnmpAccessTable  OBJECT-TYPE
	SYNTAX SEQUENCE OF MgmtSnmpAccessTableEntry
	MAX-ACCESS not-accessible
	STATUS     current
	DESCRIPTION 
		"This table holds the objects of the mgmtSnmpAccessTable."
	::= { mgmtSnmp 3 }

mgmtSnmpAccessTableEntry  OBJECT-TYPE
	SYNTAX 	MgmtSnmpAccessTableEntry
	MAX-ACCESS not-accessible
	STATUS     current
	DESCRIPTION 
		"This parameter represents the entry for the mgmtSnmpAccessTable."
	INDEX { mgmtSnmpAccessTableIndex }
	::= { mgmtSnmpAccessTable 1 }

MgmtSnmpAccessTableEntry ::= SEQUENCE {
	mgmtSnmpAccessTableIndex
		Unsigned32
}

mgmtSnmpAccessTableIndex  OBJECT-TYPE
	SYNTAX     Unsigned32 (0..20)
	MAX-ACCESS not-accessible
	STATUS     current
	DESCRIPTION 
		"This parameter represents the index for the mgmtSnmpAccessTable and this 
		 is not-accessible."
	::= { mgmtSnmpAccessTableEntry 1 }

-- SNMP Trap Host Table

mgmtSnmpTrapHostTable  OBJECT-TYPE
	SYNTAX SEQUENCE OF MgmtSnmpTrapHostTableEntry
	MAX-ACCESS not-accessible
	STATUS     current
	DESCRIPTION 
		"This table contains the destination IP address and community password 
		 for the trap delivery."
	::= { mgmtSnmp 4 }

mgmtSnmpTrapHostTableEntry  OBJECT-TYPE
	SYNTAX 	MgmtSnmpTrapHostTableEntry
	MAX-ACCESS not-accessible
	STATUS     current
	DESCRIPTION 
		"This parameter represents the entry for the mgmtSnmpTrapHostTable."
	INDEX { mgmtSnmpTrapHostTableIndex }
	::= { mgmtSnmpTrapHostTable 1 }

MgmtSnmpTrapHostTableEntry ::= SEQUENCE {
	mgmtSnmpTrapHostTableIndex
		Unsigned32,
	mgmtSnmpTrapHostTableIPAddress
		IpAddress,
	mgmtSnmpTrapHostTablePassword
		Password,
	mgmtSnmpTrapHostTableComment
		DisplayString,
	mgmtSnmpTrapHostTableEntryStatus
		RowStatus,
	mgmtSnmpTrapHostTableInetAddress
		DisplayString
}

mgmtSnmpTrapHostTableIndex  OBJECT-TYPE
	SYNTAX     Unsigned32 (1..5)
	MAX-ACCESS read-only
	STATUS     current
	DESCRIPTION 
		"This parameter represents the index for SNMP Trap Host table. This table
		                 supports upto 5 rows."
	::= { mgmtSnmpTrapHostTableEntry 1 }

mgmtSnmpTrapHostTableIPAddress  OBJECT-TYPE
	SYNTAX     IpAddress
	MAX-ACCESS read-write
	STATUS     deprecated
	DESCRIPTION 
		"This parameter is used to represent the IP address of the management station 
		 that will receive SNMP traps from the device. This is now deprecated.
		         Instead use mgmtSnmpTrapHostTableInetAddress."
	::= { mgmtSnmpTrapHostTableEntry 2 }

mgmtSnmpTrapHostTablePassword  OBJECT-TYPE
	SYNTAX     Password
	MAX-ACCESS read-write
	STATUS     current
	DESCRIPTION 
		"This parameter is used to represent the password that is sent with the SNMP 
		 trap messages to allow the host to accept or reject the traps. The trap host 
		 will accept SNMP traps if the sent password matches the host's password. 
		 This parameter returns asterisks on get. This is not allowed to set because it is 
		                 same as mgmtSnmpReadWritePassword."
	::= { mgmtSnmpTrapHostTableEntry 3 }

mgmtSnmpTrapHostTableComment  OBJECT-TYPE
	SYNTAX     DisplayString (SIZE(0..127))
	MAX-ACCESS read-write
	STATUS     current
	DESCRIPTION 
		"This parameter represents the comment for the row in the SNMP Trap Host Table."
	::= { mgmtSnmpTrapHostTableEntry 4 }

mgmtSnmpTrapHostTableEntryStatus  OBJECT-TYPE
	SYNTAX     RowStatus
	MAX-ACCESS read-write
	STATUS     current
	DESCRIPTION 
		"This parameter is used to configure the row status for the SNMP Trap 
		                 Host table. 
		                 It can be configured as 
		                 active(enable) -1, 
		                 notInService(disable) - 2, 
		                 createAndGo(create row) -4, 
		                 destroy(delete) - 6"
	::= { mgmtSnmpTrapHostTableEntry 5 }

mgmtSnmpTrapHostTableInetAddress  OBJECT-TYPE
	SYNTAX     DisplayString
	MAX-ACCESS read-write
	STATUS     current
	DESCRIPTION 
		"This parameter is used to represent the Inet address of the management station 
		 that will receive SNMP traps from the device."
	::= { mgmtSnmpTrapHostTableEntry 6 }

mgmtSnmpVersion  OBJECT-TYPE
	SYNTAX     INTEGER {
		snmpv1-v2c (1),
		snmpv3 (2)
	}
	MAX-ACCESS read-write
	STATUS     current
	DESCRIPTION 
		"This parameter is used to configure the SNMP Version. The version v2c provides the
		                 security by means of community passwords and the version v3 provides highest security 
		                 with authentication and encryption."
	DEFVAL  { snmpv1-v2c }
	::= { mgmtSnmp 5 }

mgmtSnmpV3SecurityLevel  OBJECT-TYPE
	SYNTAX     INTEGER {
		none (1),
		noAuthNoPriv (2),
		authNoPriv (3),
		authPriv (4)
	}
	MAX-ACCESS read-write
	STATUS     current
	DESCRIPTION 
		"This parameter allows to select the security level for SNMPV3. The level
		                 noAuthNoPriv is not supported."
	DEFVAL  { authPriv }
	::= { mgmtSnmp 6 }

mgmtSnmpV3AuthProtocol  OBJECT-TYPE
	SYNTAX     INTEGER {
		none (1),
		md5 (2),
		sha (3)
	}
	MAX-ACCESS read-write
	STATUS     current
	DESCRIPTION 
		"This parameter allows to configure the authentication protocol in SNMPV3. 
		                 Select 2 for MD5 and
		                        3 for SHA. "
	DEFVAL  { md5 }
	::= { mgmtSnmp 7 }

mgmtSnmpV3AuthPassword  OBJECT-TYPE
	SYNTAX     V3Password
	MAX-ACCESS read-write
	STATUS     current
	DESCRIPTION 
		"This parameter allows to configure the authentication password for the
		                 authentication protocol."
	::= { mgmtSnmp 8 }

mgmtSnmpV3PrivProtocol  OBJECT-TYPE
	SYNTAX     INTEGER {
		none (1),
		des (2),
		aes-128 (3)
	}
	MAX-ACCESS read-write
	STATUS     current
	DESCRIPTION 
		"This parameter allows to configure the privacy (encryption) protocol in SNMPV3. 
		                 Select 2 for DES and
		                        3 for AES-128. "
	DEFVAL  { des }
	::= { mgmtSnmp 9 }

mgmtSnmpV3PrivPassword  OBJECT-TYPE
	SYNTAX     V3Password
	MAX-ACCESS read-write
	STATUS     current
	DESCRIPTION 
		"This parameter allows to configure the privacy (encryption) password for the
		                 privacy protocol."
	::= { mgmtSnmp 10 }

-- ======================================================================================
-- Definition of the HTTP Group objects
-- ======================================================================================
-- HTTP Password

httpPassword  OBJECT-TYPE
	SYNTAX     Password
	MAX-ACCESS read-write
	STATUS     current
	DESCRIPTION 
		"This parameter represents the system access password for the HTTP interface 
		 to manage the device via a web browser.This parameter would return the value 
		 in asterisks."
	DEFVAL  { "public" }
	::= { http 1 }

-- HTTP Port

httpPort  OBJECT-TYPE
	SYNTAX     Unsigned32
	MAX-ACCESS read-write
	STATUS     current
	DESCRIPTION 
		"This parameter is used to configure the port on which HTTP is accessed."
	DEFVAL  { 80 }
	::= { http 2 }

-- HTTP Monitor User Password

httpSecondaryUserPassword  OBJECT-TYPE
	SYNTAX     Password
	MAX-ACCESS read-write
	STATUS     current
	DESCRIPTION 
		"This parameter represents the system access password for the HTTP interface 
		 to manage the device via a web browser.This parameter would return the value 
		 in asterisks."
	DEFVAL  { "public" }
	::= { http 3 }

-- ======================================================================================
-- Definition of the Telnet Group objects
-- ======================================================================================
-- Telnet Password

telnetPassword  OBJECT-TYPE
	SYNTAX     Password
	MAX-ACCESS read-write
	STATUS     current
	DESCRIPTION 
		"This parameter represents the system access password for the Telnet interface.
		 This parameter would return the value in asterisks."
	::= { telnet 1 }

-- Telnet Port

telnetPort  OBJECT-TYPE
	SYNTAX     Unsigned32
	MAX-ACCESS read-write
	STATUS     current
	DESCRIPTION 
		"This parameter is used to configure the port on which the Telnet is accessed."
	DEFVAL  { 23 }
	::= { telnet 2 }

-- Number of concurrent Telnet sessions

telnetSessions  OBJECT-TYPE
	SYNTAX     Unsigned32
	MAX-ACCESS read-write
	STATUS     current
	DESCRIPTION 
		"This parameter is used to configure the number of telnet sessions.
		                  A total of 10 sessions (Telnet + SSH)  are available"
	::= { telnet 3 }

-- Telnet Monitor User Password

telnetSecondaryUserPassword  OBJECT-TYPE
	SYNTAX     Password
	MAX-ACCESS read-write
	STATUS     current
	DESCRIPTION 
		"This parameter represents the system access password for the Telnet interface.
		 This parameter would return the value in asterisks."
	::= { telnet 4 }

-- ======================================================================================
-- Definition of the TFTP Group objects
-- ======================================================================================
-- TFTP Server IP Address

tftpSrvIpAddress  OBJECT-TYPE
	SYNTAX     IpAddress
	MAX-ACCESS read-write
	STATUS     deprecated
	DESCRIPTION 
		"This parameter represents the IP address of the TFTP server. This is now deprecated.
		        Instead use tftpSrvInetAddress."
	DEFVAL  { '0a00000a'H }
	::= { tftp 1 }

-- TFTP File Name

tftpFileName  OBJECT-TYPE
	SYNTAX     DisplayString (SIZE(0..50))
	MAX-ACCESS read-write
	STATUS     current
	DESCRIPTION 
		"This parameter represents the filename that is to upload or download from the TFTP server."
	::= { tftp 2 }

-- TFTP File Type

tftpFileType  OBJECT-TYPE
	SYNTAX     INTEGER {
		config (1),
		image (2),
		eventlog (3),
		templog (4),
		textConfigFile (5),
		debuglog (6),
		configProfile (7),
		retrieveUpgradeLicenseInfo (8),
		loadUpgradeLicense (9),
		retrieveUpgradeLicenses (10),
		rltReport (11),
		rltPerformance (12),
        sslCertificate (13)
	}
	MAX-ACCESS read-write
	STATUS     current
	DESCRIPTION 
		" This parameter informs the device about the type of file that is being uploaded or downloaded.
		  Select (1) if it is config file 
		         (2) if it is an image file and
		         (3) if it is an eventlog file.
		         (4) if it is a templog file.
		         (5) if it is a Text Based Config File.
		         (6) if it is a eventlog File.
		         (7) if it is a config profile File.
                 (8) if it is to  retrieve system information license file.
                 (9) if it is to  upgrade license file.
                 (10) if it is to retrieve upgrade all licenses.
                 (11) if it is to retrieve Rlt report file.
                 (12) if it is to retrieve Rlt performance file.
                 (13) if it is SSL Certificate."
	DEFVAL  { image }
	::= { tftp 3 }

-- - TFTP Operation Type

tftpOpType  OBJECT-TYPE
	SYNTAX     INTEGER {
		upload (1),
		download (2),
		downloadandReboot (3),
		none (4)
	}
	MAX-ACCESS read-write
	STATUS     current
	DESCRIPTION 
		"This parameter represents the type of TFTP operation that is to be executed.
		 The upload functionality will transfer the specified file from the device to the TFTP server. 
		 The download functionality will transfer the specified file from the TFTP server to the device. 
		 The download and reboot functionality will download the file from the TFTP server and then reboots the device. 
		 Select  (1) to upload the image, 
		         (2) to download the image and 
		         (3) to Download & Reboot the device.
		         (4) none "
	DEFVAL  { none }
	::= { tftp 4 }

-- TFTP Status

tftpOpStatus  OBJECT-TYPE
	SYNTAX     INTEGER {
		idle (1),
		downloadInProgress (2),
		downloadSuccess (3),
		downloadFailure (4),
		signatureCheckInProgress (5),
		signatureCheckFailed (6),
		writeOnFlashInProgress (7),
		writeOnFlashFailed (8),
		uploadInProgress (9),
		uploadSuccess (10),
		uploadFailure (11)
	}
	MAX-ACCESS read-only
	STATUS     current
	DESCRIPTION 
		" This parameter represents the TFTP operation status. 
		   1 - Idle,
		   2 - Download in progress
		   3 - Download Success
		   4 - Download Failure
		   5 - Signature check in progress
		   6 - Signature check failed
		   7 - Write on flash is in progress
		   8 - Write on flash is failed
		   9 - Upload in progress
		   10 - Upload success
		   11 - Upload failed"
	::= { tftp 5 }

-- TFTP Server Inet Address

tftpSrvInetAddress  OBJECT-TYPE
	SYNTAX     DisplayString
	MAX-ACCESS read-write
	STATUS     current
	DESCRIPTION 
		"This parameter represents the Inet address of the TFTP server."
	::= { tftp 6 }

-- =============================================================================
-- Definition of trapControl Group Objects : trapControl
-- =============================================================================
-- Generic Trap

genericTrap  OBJECT-TYPE
	SYNTAX     DisplayString
	MAX-ACCESS accessible-for-notify
	STATUS     current
	DESCRIPTION 
		"This parameter is used to provide additional information on traps."
	::= { trapControl 1 }

-- Global Trap Status 

globalTrapStatus  OBJECT-TYPE
	SYNTAX     INTEGER {
		enable (1),
		disable (2)
	}
	MAX-ACCESS not-accessible
	STATUS     current
	DESCRIPTION 
		"This parameter is used to enable or disable the configuration related traps and this 
		                     is not allowed to set."
	::= { trapControl 2 }

-- =============================================================================
-- Definition of Management Access Control Group Objects : mgmtAccessControl
-- =============================================================================
-- All Interfaces Access Control

allIntAccessControl  OBJECT-TYPE
	SYNTAX     INTEGER {
		enable (1),
		disable (2)
	}
	MAX-ACCESS read-write
	STATUS     current
	DESCRIPTION 
		"This parameter allows to control all management interface accesses. Select 
		 1 - enable and
		 2 - disable
		 Alert: Disabling this parameter disables all interfaces. Only serial console can
		                        be accessed for device management."
	DEFVAL  { enable }
	::= { mgmtAccessControl 1 }

-- HTTP Access Control

httpAccessControl  OBJECT-TYPE
	SYNTAX     INTEGER {
		enable (1),
		disable (2)
	}
	MAX-ACCESS read-write
	STATUS     current
	DESCRIPTION 
		"This parameter allows to enable or disable the HTTP access. Select 
		 1 - enable and
		 2 - disable"
	DEFVAL  { enable }
	::= { mgmtAccessControl 2 }

-- HTTPS Access Control

httpsAccessControl  OBJECT-TYPE
	SYNTAX     INTEGER {
		enable (1),
		disable (2)
	}
	MAX-ACCESS read-write
	STATUS     current
	DESCRIPTION 
		"This parameter allows to enable or disable the HTTPS access. Select 
		 1 - enable and
		 2 - disable"
	DEFVAL  { enable }
	::= { mgmtAccessControl 3 }

-- SNMP Access Control

snmpAccessControl  OBJECT-TYPE
	SYNTAX     INTEGER {
		enable (1),
		disable (2)
	}
	MAX-ACCESS read-write
	STATUS     current
	DESCRIPTION 
		"This parameter allows to enable or disable the SNMP access. Select 
		 1 - enable and
		 2 - disable"
	DEFVAL  { enable }
	::= { mgmtAccessControl 4 }

-- TELNET Access Control

telnetAccessControl  OBJECT-TYPE
	SYNTAX     INTEGER {
		enable (1),
		disable (2)
	}
	MAX-ACCESS read-write
	STATUS     current
	DESCRIPTION 
		"This parameter allows to enable or disable the TELNET access. Select 
		 1 - enable and
		 2 - disable"
	DEFVAL  { enable }
	::= { mgmtAccessControl 5 }

-- SSH Access Control

sshAccessControl  OBJECT-TYPE
	SYNTAX     INTEGER {
		enable (1),
		disable (2)
	}
	MAX-ACCESS read-write
	STATUS     current
	DESCRIPTION 
		"This parameter allows to enable or disable the SSH access. Select 
		 1 - enable and
		 2 - disable"
	DEFVAL  { enable }
	::= { mgmtAccessControl 6 }

-- Management Table Status

mgmtAccessTableStatus  OBJECT-TYPE
	SYNTAX     INTEGER {
		enable (1),
		disable (2)
	}
	MAX-ACCESS read-write
	STATUS     current
	DESCRIPTION 
		"This parameter allows to enable or disable the Management Access Table.
		                 Enabling this parameter allows the traffic from only the IP address
		                 specified in the Management Access Table. Select 
		 1 - enable and
		 2 - disable"
	DEFVAL  { disable }
	::= { mgmtAccessControl 7 }

-- Management Access Table

mgmtAccessTable  OBJECT-TYPE
	SYNTAX SEQUENCE OF MgmtAccessTableEntry
	MAX-ACCESS not-accessible
	STATUS     current
	DESCRIPTION 
		"This table provides the facility to allow the traffic from a particular
		 machine identified by the IP address."
	::= { mgmtAccessControl 8 }

mgmtAccessTableEntry  OBJECT-TYPE
	SYNTAX 	MgmtAccessTableEntry
	MAX-ACCESS not-accessible
	STATUS     current
	DESCRIPTION 
		"This parameter represents the entry for the Management Access Table. It can hold a 
		 maximum of 5 entries."
	INDEX { mgmtAccessTableIndex }
	::= { mgmtAccessTable 1 }

MgmtAccessTableEntry ::= SEQUENCE {
	mgmtAccessTableIndex
		Unsigned32,
	mgmtAccessTableIpAddress
		IpAddress,
	mgmtAccessTableEntryStatus
		RowStatus,
	mgmtAccessTableInetAddress
		InetAddress
}

mgmtAccessTableIndex  OBJECT-TYPE
	SYNTAX     Unsigned32
	MAX-ACCESS read-only
	STATUS     current
	DESCRIPTION 
		"This parameter represents the index of the Management Access Table."
	::= { mgmtAccessTableEntry 1 }

mgmtAccessTableIpAddress  OBJECT-TYPE
	SYNTAX     IpAddress
	MAX-ACCESS read-write
	STATUS     deprecated
	DESCRIPTION 
		"This parameter holds the IP address of the machine to which traffic need to be
		 allowed. This is now deprecated. Instead use mgmtAccessTableInetAddress."
	::= { mgmtAccessTableEntry 2 }

mgmtAccessTableEntryStatus  OBJECT-TYPE
	SYNTAX     RowStatus
	MAX-ACCESS read-write
	STATUS     current
	DESCRIPTION 
		"This parameter represents the entry status for the Management Access Table.
		 It can be configured as 
		                 active(enable) -1, 
		                 notInService(disable) - 2, 
		                 createAndGo(create row) -4, 
		                 destroy(delete) - 6"
	::= { mgmtAccessTableEntry 3 }

mgmtAccessTableInetAddress  OBJECT-TYPE
	SYNTAX     InetAddress
	MAX-ACCESS read-write
	STATUS     current
	DESCRIPTION 
		"This parameter holds the Inet address of the machine to which traffic need to be
		 allowed."
	::= { mgmtAccessTableEntry 4 }

-- ======================================================================================
-- Definition of the SSH subgroup objects : ssh
-- ======================================================================================
-- SSH Port

sshPort  OBJECT-TYPE
	SYNTAX     Unsigned32
	MAX-ACCESS read-write
	STATUS     current
	DESCRIPTION 
		"This parameter is used to configure the port on which SSH is accessed."
	DEFVAL  { 22 }
	::= { ssh 1 }

-- Number of concurrent SSH sessions

sshSessions  OBJECT-TYPE
	SYNTAX     Unsigned32
	MAX-ACCESS read-write
	STATUS     current
	DESCRIPTION 
		"This parameter is used to set the number of concurrent SSH sessions."
	::= { ssh 2 }

-- ======================================================================================
-- Definition of the Auto Config Recovery subgroup objects : autoConfigRecovery
-- ======================================================================================
-- Auto Config Recovery Status

autoConfigRecoveryStatus  OBJECT-TYPE
	SYNTAX     INTEGER {
		enable (1),
		disable (2)
	}
	MAX-ACCESS read-write
	STATUS     current
	DESCRIPTION 
		"This parameter allows to enable or disable the Auto Config Recovery for QB
		          End point A or End Point B.
		            1 - enable and
		            2 - disable"
	::= { autoConfigRecovery 1 }

-- Auto Config Recovery Delay

autoConfigRecoveryDelay  OBJECT-TYPE
	SYNTAX     Unsigned32 (30..300)
	MAX-ACCESS read-write
	STATUS     current
	DESCRIPTION 
		"This parameter allows to configure Auto Recovery Delay"
	::= { autoConfigRecovery 2 }

-- ======================================================================================
-- Definition of the HTTPS subgroup objects : 
-- ======================================================================================
-- Https TLS 1.2 OnlyStatus



httpsTLS1dot2only  OBJECT-TYPE
	SYNTAX     INTEGER {
		enable (1),
		disable (2)
	}
	MAX-ACCESS read-write
	STATUS     current
	DESCRIPTION 
		"This parameter allows to enable or disable TLS1.2 Only Status.
          1- enable
          2- disable"
                         
	::= { https 1 }

-- bleStatus

bleStatus  OBJECT-TYPE
	SYNTAX     INTEGER {
		enable (1),
		disable (2)
	}
	MAX-ACCESS read-write
	STATUS     current
	DESCRIPTION 
		"This parameter is used to configure the bluetooth status 
		1. Enable
		2. Disable"
	DEFVAL  { enable }
	::= { ble 1 }

-- bleName

bleName  OBJECT-TYPE
	SYNTAX     DisplayString (SIZE(6..16))
	MAX-ACCESS read-write
	STATUS     current
	DESCRIPTION 
		"This parameter is used to configure bluetooth name min.6 to max 16 characters"
	::= { ble 2 }

-- blePasskey

blePasskey  OBJECT-TYPE
	SYNTAX     DisplayString (SIZE(6))
	MAX-ACCESS read-write
	STATUS     current
	DESCRIPTION 
		"This paramater is used to configure bluetooth passkey of 6 characters"
	::= { ble 3 }

-- bleConnectionStatus

bleConnectionStatus  OBJECT-TYPE
	SYNTAX     DisplayString (SIZE(64))
	MAX-ACCESS read-only
	STATUS     current
	DESCRIPTION 
		"This parameter is used to get the bluetooth connection status"
	::= { ble 4 }

-- bleDisconnect

bleDisconnect  OBJECT-TYPE
	SYNTAX     INTEGER {
		yes (1),
		no (2)
	}
	MAX-ACCESS read-write
	STATUS     current
	DESCRIPTION 
		"This parameter is used to disconnect bluetooth 
		1. yes
		2. no"
	DEFVAL  { no }
	::= { ble 5 }

-- ======================================================================================
-- Definition of the Device Monitoring Group objects
-- ======================================================================================
-- ======================================================================================
-- Definition of the Syslog Group objects : syslog
-- ======================================================================================
-- Syslog Status

syslogStatus  OBJECT-TYPE
	SYNTAX     INTEGER {
		enable (1),
		disable (2)
	}
	MAX-ACCESS read-write
	STATUS     current
	DESCRIPTION 
		" This parameter is used to configure the status for the sysLog.
		  Select 
		  1 to enable the Syslog status and 
		  2 to disable the syslog status."
	DEFVAL  { enable }
	::= { syslog 1 }

-- Syslog Priority

syslogPriority  OBJECT-TYPE
	SYNTAX     INTEGER {
		emergency (1),
		alert (2),
		critical (3),
		error (4),
		warning (5),
		notice (6),
		info (7),
		debug (8)
	}
	MAX-ACCESS read-write
	STATUS     current
	DESCRIPTION 
		" This parameter is used to configure the priority for the syslog.
		  Select 
		  1 for emergency, 
		  2 for alert, 
		  3 for critical, 
		  4 for error,
		  5 for warning, 
		  6 for notice, 
		  7 for info and 
		  8 for debug."
	DEFVAL  { warning }
	::= { syslog 2 }

syslogReset  OBJECT-TYPE
	SYNTAX     INTEGER {
		yes (1),
		no (2)
	}
	MAX-ACCESS read-write
	STATUS     current
	DESCRIPTION 
		"This parameter is used to reset or clear the syslog. Select
		                1 - to reset or clear
		                2 - none."
	DEFVAL  { no }
	::= { syslog 3 }

-- Syslog Host Table

syslogHostTable  OBJECT-TYPE
	SYNTAX SEQUENCE OF SyslogHostTableEntry
	MAX-ACCESS not-accessible
	STATUS     current
	DESCRIPTION 
		"This table contains the syslog configurations."
	::= { syslog 4 }

syslogHostTableEntry  OBJECT-TYPE
	SYNTAX 	SyslogHostTableEntry
	MAX-ACCESS not-accessible
	STATUS     current
	DESCRIPTION 
		"This parameter represents the entry for the syslogHostTable."
	INDEX { syslogHostTableIndex }
	::= { syslogHostTable 1 }

SyslogHostTableEntry ::= SEQUENCE {
	syslogHostTableIndex
		Unsigned32,
	syslogHostIpAddress
		IpAddress,
	syslogHostPort
		Unsigned32,
	syslogHostComment
		DisplayString,
	syslogHostTableEntryStatus
		RowStatus,
	syslogHostInetAddress
		DisplayString
}

syslogHostTableIndex  OBJECT-TYPE
	SYNTAX     Unsigned32
	MAX-ACCESS read-only
	STATUS     current
	DESCRIPTION 
		"This parameter is used to index the syslogHostTable."
	::= { syslogHostTableEntry 1 }

syslogHostIpAddress  OBJECT-TYPE
	SYNTAX     IpAddress
	MAX-ACCESS read-write
	STATUS     deprecated
	DESCRIPTION 
		"This parameter is used to represent the IP address for which syslog messages 
		 to be sent. This is now deprecated. Instead use syslogHostInetAddress."
	::= { syslogHostTableEntry 2 }

syslogHostPort  OBJECT-TYPE
	SYNTAX     Unsigned32
	MAX-ACCESS read-write
	STATUS     current
	DESCRIPTION 
		"This parameter is used to represents the host port number for which the syslog 
		 messages are sent."
	::= { syslogHostTableEntry 3 }

syslogHostComment  OBJECT-TYPE
	SYNTAX     DisplayString (SIZE(0..32))
	MAX-ACCESS read-write
	STATUS     current
	DESCRIPTION 
		"This parameter displays the comment for the host port of the syslog table."
	::= { syslogHostTableEntry 4 }

syslogHostTableEntryStatus  OBJECT-TYPE
	SYNTAX     RowStatus
	MAX-ACCESS read-write
	STATUS     current
	DESCRIPTION 
		"This parameter is used to configue the status of the Syslog host entry table.
		 A maximum of 5 entries can be added to this table.
		 It can be configured as 
		                 active(enable) -1, 
		                 notInService(disable) - 2, 
		                 createAndGo(create row) -4, 
		                 destroy(delete) - 6"
	::= { syslogHostTableEntry 5 }

syslogHostInetAddress  OBJECT-TYPE
	SYNTAX     DisplayString
	MAX-ACCESS read-write
	STATUS     current
	DESCRIPTION 
		"This parameter is used to represent the Inet address for which syslog messages 
		 to be sent."
	::= { syslogHostTableEntry 6 }

-- ======================================================================================
-- Definition of the Eventlog Group objects : eventlog
-- ======================================================================================
-- Eventlog Priority

eventLogPriority  OBJECT-TYPE
	SYNTAX     INTEGER {
		emergency (1),
		alert (2),
		critical (3),
		error (4),
		warning (5),
		notice (6),
		info (7),
		debug (8)
	}
	MAX-ACCESS read-write
	STATUS     current
	DESCRIPTION 
		"This parameter is used to configure the priority for the event log 
		 table. Select 
		 1 for Emergency, 
		 2 for alert, 
		 3 for critical, 
		 4 for error, 
		 5 for warning, 
		 6 for notice, 
		 7 for info and 
		 8 for debug."
	DEFVAL  { warning }
	::= { eventlog 1 }

-- Eventlog Reset

eventLogReset  OBJECT-TYPE
	SYNTAX     INTEGER {
		yes (1),
		no (2)
	}
	MAX-ACCESS read-write
	STATUS     current
	DESCRIPTION 
		"This parameter is used to reset/clear the event log table. 
		 When this parameter is set, then all enteries in the event log table 
		 are deleted/cleared. Select (1) to reset the table. 
		 "
	DEFVAL  { no }
	::= { eventlog 2 }

-- ======================================================================================
-- Definition of the SNTP Group objects : sntp
-- ======================================================================================
-- SNTP Status

sntpStatus  OBJECT-TYPE
	SYNTAX     INTEGER {
		enable (1),
		disable (2)
	}
	MAX-ACCESS read-write
	STATUS     current
	DESCRIPTION 
		"This parameter is used to enable or disable the SNTP functionality. 
		 Select 
		 1 to enable SNTP and 
		 2 to Disable the SNTP functionality. "
	DEFVAL  { disable }
	::= { sntp 1 }

-- SNTP Primary Server Name

sntpPrimaryServerName  OBJECT-TYPE
	SYNTAX     DisplayString (SIZE(0..32))
	MAX-ACCESS read-write
	STATUS     deprecated
	DESCRIPTION 
		"This parameter is used for the primary SNTP server name. This is now deprecated.
		        Instead use sntpPrimaryServerInetAddress."
	DEFVAL  { "time.nist.gov" }
	::= { sntp 2 }

-- SNTP Secondary Server Name

sntpSecondaryServerName  OBJECT-TYPE
	SYNTAX     DisplayString (SIZE(0..32))
	MAX-ACCESS read-write
	STATUS     deprecated
	DESCRIPTION 
		"This parameter is used for the secondary SNTP server name. This is now deprecated.
		        Instead use sntpSecondaryServerInetAddress."
	::= { sntp 3 }

-- SNTP Time Zone

sntpTimeZone  OBJECT-TYPE
	SYNTAX     INTEGER {
		dateline (1),
		samoa (2),
		hawaii (3),
		alaska (4),
		pacific-us (5),
		mountain-us (6),
		arizona (7),
		central-us (8),
		mexico-city (9),
		eastern-us (10),
		indiana (11),
		atlantic-canada (12),
		santiago (13),
		ewfoundland (14),
		brasilia (15),
		buenos-aires (16),
		mid-atlantic (17),
		azores (18),
		london (19),
		western-europe (20),
		eastern-europe (21),
		cairo (22),
		russia-iraq (23),
		iran (24),
		arabian (25),
		afghanistan (26),
		pakistan (27),
		india (28),
		bangladesh (29),
		burma (30),
		bangkok (31),
		australia-wt (32),
		hong-kong (33),
		beijing (34),
		japan-korea (35),
		australia-ct (36),
		australia-et (37),
		central-pacific (38),
		new-zealand (39),
		tonga (40),
		western-samoa (41)
	}
	MAX-ACCESS read-write
	STATUS     current
	DESCRIPTION 
		"This parameter is used to specify the appropriate time zone. 
		 dateline(1),     
		 samoa(2),    
		 hawaii(3),      
		 alaska(4),       
		 pacific-us(5),  
		 mountain-us(6),  
		 arizona(7),  
		 central-us(8),  
		 mexico-city(9),  
		 eastern-us(10), 
		 indiana(11),  
		 atlantic-canada(12),  
		 santiago(13), 
		 ewfoundland(14),  
		 brasilia(15),  
		 buenos-aires(16),  
		 mid-atlantic(17),  
		 azores(18),  
		 london(19), 
		 western-europe(20),  
		 eastern-europe(21),  
		 cairo(22),  
		 russia-iraq(23),  
		 iran(24),  
		 arabian(25), 
		 afghanistan(26),  
		 pakistan(27),  
		 india(28),  
		 bangladesh(29),  
		 burma(30),  
		 bangkok(31), 
		 australia-wt(32),  
		 hong-kong(33),  
		 beijing(34),  
		 japan-korea(35),  
		 australia-ct(36), 
		 australia-et(37),  
		 central-pacific(38),  
		 new-zealand(39),  
		 tonga(40), 
		 western-samoa(41)
		 "
	::= { sntp 4 }

-- SNTP Day Light Saving Time

sntpDayLightSavingTime  OBJECT-TYPE
	SYNTAX     INTEGER {
		plus-two (1),
		plus-one (2),
		unchanged (3),
		minus-one (4),
		minus-two (5)
	}
	MAX-ACCESS read-write
	STATUS     current
	DESCRIPTION 
		"This parameter is used to indicate the number of hours to adjust 
		 for Daylight Saving Time. 
		 plus-two(1), 
		 plus-one(2), 
		 unchanged(3),
		 minus-one(4), 
		 minus-two(5)"
	DEFVAL  { unchanged }
	::= { sntp 5 }

-- SNTP Current Time

sntpShowCurrentTime  OBJECT-TYPE
	SYNTAX     DisplayString
	MAX-ACCESS read-only
	STATUS     current
	DESCRIPTION 
		"This parameter displays the current time got from the SNTP server"
	::= { sntp 6 }

-- SNTP re-sync interval

sntpReSyncInterval  OBJECT-TYPE
	SYNTAX     Integer32 (0..1440)
	MAX-ACCESS read-write
	STATUS     current
	DESCRIPTION 
		" This parameter allows user to configure the sntp client 
		  re-sync time."
	DEFVAL  { 0 }
	::= { sntp 7 }

-- SNTP Current Date and Time

sntpCurrentDateAndTime  OBJECT-TYPE
	SYNTAX     DisplayString
	MAX-ACCESS read-write
	STATUS     current
	DESCRIPTION 
		"This parameter allows user to configure current data and time manually."
	::= { sntp 8 }

-- SNTP Current Date and Time

sntpSyncStatus  OBJECT-TYPE
	SYNTAX     INTEGER {
		disabled (1),
		synchronizing (2),
		synchronized (3)
	}
	MAX-ACCESS read-only
	STATUS     current
	DESCRIPTION 
		"This parameter indicates the current status of time synchronization."
	DEFVAL  { disabled }
	::= { sntp 9 }

-- SNTP Primary Server Inet Address

sntpPrimaryServerInetAddress  OBJECT-TYPE
	SYNTAX     DisplayString
	MAX-ACCESS read-write
	STATUS     current
	DESCRIPTION 
		"This parameter is used for the primary SNTP server inet address. "
	::= { sntp 10 }

-- SNTP Secondary Server Inet Address

sntpSecondaryServerInetAddress  OBJECT-TYPE
	SYNTAX     DisplayString
	MAX-ACCESS read-write
	STATUS     current
	DESCRIPTION 
		"This parameter is used for the secondary SNTP server inet address."
	::= { sntp 11 }

-- ======================================================================================
-- Definition of the Wireless Interface Monitoring Group objects : wirelessIfStaStats
-- ======================================================================================
-- ======================================================================================
-- Definition of the Wireless Interface Station Statistics Subgroup objects : wirelessIfStaStats
-- ======================================================================================
-- Wireless Interface Station Statistics Table

wirelessIfStaStatsTable  OBJECT-TYPE
	SYNTAX SEQUENCE OF WirelessIfStaStatsTableEntry
	MAX-ACCESS not-accessible
	STATUS     current
	DESCRIPTION 
		"This table contains wireless stations statistics."
	::= { wirelessIfStaStats 1 }

wirelessIfStaStatsTableEntry  OBJECT-TYPE
	SYNTAX 	WirelessIfStaStatsTableEntry
	MAX-ACCESS not-accessible
	STATUS     current
	DESCRIPTION 
		"This parameter represents the entry for wirelessIfStaStatsTable.
		 This is indexed by interface and VAP numbers."
	INDEX { wirelessIfStaStatsTableIndex, 
		wirelessIfStaStatsTableSecIndex }
	::= { wirelessIfStaStatsTable 1 }

WirelessIfStaStatsTableEntry ::= SEQUENCE {
	wirelessIfStaStatsTableIndex
		Unsigned32,
	wirelessIfStaStatsTableSecIndex
		Unsigned32,
	wirelessIfStaStatsIfNumber
		Unsigned32,
	wirelessIfStaStatsVAPNumber
		Unsigned32,
	wirelessIfStaStatsMACAddress
		MacAddress,
	wirelessIfStaStatsRxMgmtFrames
		Counter32,
	wirelessIfStaStatsRxControlFrames
		Counter32,
	wirelessIfStaStatsRxUnicastFrames
		Counter32,
	wirelessIfStaStatsRxMulticastFrames
		Counter32,
	wirelessIfStaStatsRxBytes
		Counter32,
	wirelessIfStaStatsRxBeacons
		Counter32,
	wirelessIfStaStatsRxProbeResp
		Counter32,
	wirelessIfStaStatsRxDupFrames
		Counter32,
	wirelessIfStaStatsRxNoPrivacy
		Counter32,
	wirelessIfStaStatsRxWepFail
		Counter32,
	wirelessIfStaStatsRxDeMicFail
		Counter32,
	wirelessIfStaStatsRxDecapFailed
		Counter32,
	wirelessIfStaStatsRxDefragFailed
		Counter32,
	wirelessIfStaStatsRxDisassociationFrames
		Counter32,
	wirelessIfStaStatsRxDeauthenticationFrames
		Counter32,
	wirelessIfStaStatsRxDecryptFailedOnCRC
		Counter32,
	wirelessIfStaStatsRxUnauthPort
		Counter32,
	wirelessIfStaStatsRxUnencrypted
		Counter32,
	wirelessIfStaStatsTxDataFrames
		Counter32,
	wirelessIfStaStatsTxMgmtFrames
		Counter32,
	wirelessIfStaStatsTxUnicastFrames
		Counter32,
	wirelessIfStaStatsTxMulticastFrames
		Counter32,
	wirelessIfStaStatsTxBytes
		Counter32,
	wirelessIfStaStatsTxProbeReq
		Counter32,
	wirelessIfStaStatsTxEospLost
		Counter32,
	wirelessIfStaStatsTxPSDiscard
		Counter32,
	wirelessIfStaStatsTxAssociationFrames
		Counter32,
	wirelessIfStaStatsTxAssociationFailedFrames
		Counter32,
	wirelessIfStaStatsTxAuthenticationFrames
		Counter32,
	wirelessIfStaStatsTxAuthenticationFailed
		Counter32,
	wirelessIfStaStatsTxDeAuthFrames
		Counter32,
	wirelessIfStaStatsTxDeAuthCode
		Counter32,
	wirelessIfStaStatsTxDisassociation
		Counter32,
	wirelessIfStaStatsTxDisassociationCode
		Unsigned32,
	wirelessIfStaStatsFrequency
		Unsigned32,
	wirelessIfStaStatsState
		Unsigned32,
	wirelessIfStaStatsRSSI
		Unsigned32,
	wirelessIfStaStatsTxRate
		Unsigned32,
	wirelessIfStaStatsAuthenAlgorithm
		Unsigned32,
	wirelessIfStaStatsAssociationID
		Unsigned32,
	wirelessIfStaStatsVlanTag
		Unsigned32,
	wirelessIfStaStatsAssocationTime
		Unsigned32,
	wirelessIfStaStatsTxPower
		Unsigned32,
	wirelessIfStaStatsInactivityTimer
		Unsigned32,
	wirelessIfStaStatsStationOperatingMode
		Unsigned32,
	wirelessIfStaStatsHTCapability
		Unsigned32
}

wirelessIfStaStatsTableIndex  OBJECT-TYPE
	SYNTAX     Unsigned32 (1..16)
	MAX-ACCESS read-only
	STATUS     current
	DESCRIPTION 
		"This parameter represents the index for the wirelessIfStaStatsTable."
	::= { wirelessIfStaStatsTableEntry 1 }

wirelessIfStaStatsTableSecIndex  OBJECT-TYPE
	SYNTAX     Unsigned32 (1..255)
	MAX-ACCESS read-only
	STATUS     current
	DESCRIPTION 
		"This parameter is user defined represents the index of the 
		 stations statistics wireless interface table. This table 
		 is limited to 255 entries."
	::= { wirelessIfStaStatsTableEntry 2 }

wirelessIfStaStatsIfNumber  OBJECT-TYPE
	SYNTAX     Unsigned32 (1..2)
	MAX-ACCESS read-only
	STATUS     current
	DESCRIPTION 
		"This parameter represents the number of the station statistics 
		 for wireless interface table. You can configure up to 2 entries."
	::= { wirelessIfStaStatsTableEntry 3 }

wirelessIfStaStatsVAPNumber  OBJECT-TYPE
	SYNTAX     Unsigned32 (1..4)
	MAX-ACCESS read-only
	STATUS     current
	DESCRIPTION 
		"The parameter represents the VAP that can be configured for 
		 wireless interface. You can configure up to 4."
	::= { wirelessIfStaStatsTableEntry 4 }

wirelessIfStaStatsMACAddress  OBJECT-TYPE
	SYNTAX     MacAddress
	MAX-ACCESS read-only
	STATUS     current
	DESCRIPTION 
		"This parameter represents the MAC address of the station for 
		 wireless interface for which the statistics are gathered."
	::= { wirelessIfStaStatsTableEntry 5 }

wirelessIfStaStatsRxMgmtFrames  OBJECT-TYPE
	SYNTAX     Counter32
	MAX-ACCESS read-only
	STATUS     current
	DESCRIPTION 
		"This parameter represents the Management frames that are recevied.."
	::= { wirelessIfStaStatsTableEntry 6 }

wirelessIfStaStatsRxControlFrames  OBJECT-TYPE
	SYNTAX     Counter32
	MAX-ACCESS read-only
	STATUS     current
	DESCRIPTION 
		"This parameter represnets the control frames that are recevied."
	::= { wirelessIfStaStatsTableEntry 7 }

wirelessIfStaStatsRxUnicastFrames  OBJECT-TYPE
	SYNTAX     Counter32
	MAX-ACCESS read-only
	STATUS     current
	DESCRIPTION 
		"This parameter represents the unicast frames that are recevied."
	::= { wirelessIfStaStatsTableEntry 8 }

wirelessIfStaStatsRxMulticastFrames  OBJECT-TYPE
	SYNTAX     Counter32
	MAX-ACCESS read-only
	STATUS     current
	DESCRIPTION 
		"This parameter represents the multicast frames that are recevied."
	::= { wirelessIfStaStatsTableEntry 9 }

wirelessIfStaStatsRxBytes  OBJECT-TYPE
	SYNTAX     Counter32
	MAX-ACCESS read-only
	STATUS     current
	DESCRIPTION 
		"This parameter represents the number of bytes received."
	::= { wirelessIfStaStatsTableEntry 10 }

wirelessIfStaStatsRxBeacons  OBJECT-TYPE
	SYNTAX     Counter32
	MAX-ACCESS read-only
	STATUS     current
	DESCRIPTION 
		"This parameter represents the number of beacons received."
	::= { wirelessIfStaStatsTableEntry 11 }

wirelessIfStaStatsRxProbeResp  OBJECT-TYPE
	SYNTAX     Counter32
	MAX-ACCESS read-only
	STATUS     current
	DESCRIPTION 
		"This parameter represents the number of probe requests recevied."
	::= { wirelessIfStaStatsTableEntry 12 }

wirelessIfStaStatsRxDupFrames  OBJECT-TYPE
	SYNTAX     Counter32
	MAX-ACCESS read-only
	STATUS     current
	DESCRIPTION 
		"This parameter represents the duplicate frames recevied."
	::= { wirelessIfStaStatsTableEntry 13 }

wirelessIfStaStatsRxNoPrivacy  OBJECT-TYPE
	SYNTAX     Counter32
	MAX-ACCESS read-only
	STATUS     current
	DESCRIPTION 
		"This parameter represents the no privacy information recevied."
	::= { wirelessIfStaStatsTableEntry 14 }

wirelessIfStaStatsRxWepFail  OBJECT-TYPE
	SYNTAX     Counter32
	MAX-ACCESS read-only
	STATUS     current
	DESCRIPTION 
		"This parameter represents the failed WEP information recevied."
	::= { wirelessIfStaStatsTableEntry 15 }

wirelessIfStaStatsRxDeMicFail  OBJECT-TYPE
	SYNTAX     Counter32
	MAX-ACCESS read-only
	STATUS     current
	DESCRIPTION 
		"This parameter represents the failed deMIC information recevied."
	::= { wirelessIfStaStatsTableEntry 16 }

wirelessIfStaStatsRxDecapFailed  OBJECT-TYPE
	SYNTAX     Counter32
	MAX-ACCESS read-only
	STATUS     current
	DESCRIPTION 
		"This parameter represents the failed decapulation information 
		 recevied."
	::= { wirelessIfStaStatsTableEntry 17 }

wirelessIfStaStatsRxDefragFailed  OBJECT-TYPE
	SYNTAX     Counter32
	MAX-ACCESS read-only
	STATUS     current
	DESCRIPTION 
		"This parameter represents the failed defragmentation information
		 recevied."
	::= { wirelessIfStaStatsTableEntry 18 }

wirelessIfStaStatsRxDisassociationFrames  OBJECT-TYPE
	SYNTAX     Counter32
	MAX-ACCESS read-only
	STATUS     current
	DESCRIPTION 
		"This parameter represents the disassociated frames that are 
		 recevied."
	::= { wirelessIfStaStatsTableEntry 19 }

wirelessIfStaStatsRxDeauthenticationFrames  OBJECT-TYPE
	SYNTAX     Counter32
	MAX-ACCESS read-only
	STATUS     current
	DESCRIPTION 
		"This parameter represents the deauthenticated frames that 
		 are recevied."
	::= { wirelessIfStaStatsTableEntry 20 }

wirelessIfStaStatsRxDecryptFailedOnCRC  OBJECT-TYPE
	SYNTAX     Counter32
	MAX-ACCESS read-only
	STATUS     current
	DESCRIPTION 
		"This parameter represents the decrypt information failed on CRC
		 recevied."
	::= { wirelessIfStaStatsTableEntry 21 }

wirelessIfStaStatsRxUnauthPort  OBJECT-TYPE
	SYNTAX     Counter32
	MAX-ACCESS read-only
	STATUS     current
	DESCRIPTION 
		"This parameter represents the unauthorized port information recevied."
	::= { wirelessIfStaStatsTableEntry 22 }

wirelessIfStaStatsRxUnencrypted  OBJECT-TYPE
	SYNTAX     Counter32
	MAX-ACCESS read-only
	STATUS     current
	DESCRIPTION 
		"This parameter represents the unencrypted information recevied."
	::= { wirelessIfStaStatsTableEntry 23 }

wirelessIfStaStatsTxDataFrames  OBJECT-TYPE
	SYNTAX     Counter32
	MAX-ACCESS read-only
	STATUS     current
	DESCRIPTION 
		"This parameter represents the data frames that are transmitted."
	::= { wirelessIfStaStatsTableEntry 24 }

wirelessIfStaStatsTxMgmtFrames  OBJECT-TYPE
	SYNTAX     Counter32
	MAX-ACCESS read-only
	STATUS     current
	DESCRIPTION 
		"This parameter represents the management frames that are transmitted."
	::= { wirelessIfStaStatsTableEntry 25 }

wirelessIfStaStatsTxUnicastFrames  OBJECT-TYPE
	SYNTAX     Counter32
	MAX-ACCESS read-only
	STATUS     current
	DESCRIPTION 
		"This parameter represents the number of unicast frames from 
		 the station that are further transmitted either by the 
		 bridge/router or by the internal host.
		"
	::= { wirelessIfStaStatsTableEntry 26 }

wirelessIfStaStatsTxMulticastFrames  OBJECT-TYPE
	SYNTAX     Counter32
	MAX-ACCESS read-only
	STATUS     current
	DESCRIPTION 
		"This parameter represents the number of multicast frames from 
		 the station that are further transmitted either by the bridge/router 
		 or by the internal host.
		"
	::= { wirelessIfStaStatsTableEntry 27 }

wirelessIfStaStatsTxBytes  OBJECT-TYPE
	SYNTAX     Counter32
	MAX-ACCESS read-only
	STATUS     current
	DESCRIPTION 
		"This parameter represents the number of bytes from the station 
		 that are further transmitted either by the bridge/router or by 
		 the internal host."
	::= { wirelessIfStaStatsTableEntry 28 }

wirelessIfStaStatsTxProbeReq  OBJECT-TYPE
	SYNTAX     Counter32
	MAX-ACCESS read-only
	STATUS     current
	DESCRIPTION 
		"This parameter represents the number of transmitted probe request
		 from the station either by the bridge/router or by internal host."
	::= { wirelessIfStaStatsTableEntry 29 }

wirelessIfStaStatsTxEospLost  OBJECT-TYPE
	SYNTAX     Counter32
	MAX-ACCESS read-only
	STATUS     current
	DESCRIPTION 
		"This parameter represents the end of service period."
	::= { wirelessIfStaStatsTableEntry 30 }

wirelessIfStaStatsTxPSDiscard  OBJECT-TYPE
	SYNTAX     Counter32
	MAX-ACCESS read-only
	STATUS     current
	DESCRIPTION 
		"This parameter displays the power save mode. "
	::= { wirelessIfStaStatsTableEntry 31 }

wirelessIfStaStatsTxAssociationFrames  OBJECT-TYPE
	SYNTAX     Counter32
	MAX-ACCESS read-only
	STATUS     current
	DESCRIPTION 
		"This parameter represents the number of associated frames 
		 transmitted."
	::= { wirelessIfStaStatsTableEntry 32 }

wirelessIfStaStatsTxAssociationFailedFrames  OBJECT-TYPE
	SYNTAX     Counter32
	MAX-ACCESS read-only
	STATUS     current
	DESCRIPTION 
		"This parameter represents the number of the failed associated 
		 frames transmitted. "
	::= { wirelessIfStaStatsTableEntry 33 }

wirelessIfStaStatsTxAuthenticationFrames  OBJECT-TYPE
	SYNTAX     Counter32
	MAX-ACCESS read-only
	STATUS     current
	DESCRIPTION 
		"This parameter represents the number of the authentication 
		 frames transmitted."
	::= { wirelessIfStaStatsTableEntry 34 }

wirelessIfStaStatsTxAuthenticationFailed  OBJECT-TYPE
	SYNTAX     Counter32
	MAX-ACCESS read-only
	STATUS     current
	DESCRIPTION 
		"This parameter represents the failed authentication frames."
	::= { wirelessIfStaStatsTableEntry 35 }

wirelessIfStaStatsTxDeAuthFrames  OBJECT-TYPE
	SYNTAX     Counter32
	MAX-ACCESS read-only
	STATUS     current
	DESCRIPTION 
		"This parameter represents the deauthorized frames transmitted."
	::= { wirelessIfStaStatsTableEntry 36 }

wirelessIfStaStatsTxDeAuthCode  OBJECT-TYPE
	SYNTAX     Counter32
	MAX-ACCESS read-only
	STATUS     current
	DESCRIPTION 
		"This parameter represents the deauthorized code transmitted."
	::= { wirelessIfStaStatsTableEntry 37 }

wirelessIfStaStatsTxDisassociation  OBJECT-TYPE
	SYNTAX     Counter32
	MAX-ACCESS read-only
	STATUS     current
	DESCRIPTION 
		"This parameter represents the disassociation information 
		 transmitted."
	::= { wirelessIfStaStatsTableEntry 38 }

wirelessIfStaStatsTxDisassociationCode  OBJECT-TYPE
	SYNTAX     Unsigned32
	MAX-ACCESS read-only
	STATUS     current
	DESCRIPTION 
		"This parameter representd the disassociation code transmitted."
	::= { wirelessIfStaStatsTableEntry 39 }

wirelessIfStaStatsFrequency  OBJECT-TYPE
	SYNTAX     Unsigned32
	MAX-ACCESS read-only
	STATUS     current
	DESCRIPTION 
		"This parameter represents the frequency on which the station is 
		 operating."
	::= { wirelessIfStaStatsTableEntry 40 }

wirelessIfStaStatsState  OBJECT-TYPE
	SYNTAX     Unsigned32
	MAX-ACCESS read-only
	STATUS     current
	DESCRIPTION 
		"This parameter represents the present state of the station."
	::= { wirelessIfStaStatsTableEntry 41 }

wirelessIfStaStatsRSSI  OBJECT-TYPE
	SYNTAX     Unsigned32
	MAX-ACCESS read-only
	STATUS     current
	DESCRIPTION 
		"This parameter represents the RSSI (received signal strength) of the station."
	::= { wirelessIfStaStatsTableEntry 42 }

wirelessIfStaStatsTxRate  OBJECT-TYPE
	SYNTAX     Unsigned32
	MAX-ACCESS read-only
	STATUS     current
	DESCRIPTION 
		"This parameter represents the transmission rate of the station."
	::= { wirelessIfStaStatsTableEntry 43 }

wirelessIfStaStatsAuthenAlgorithm  OBJECT-TYPE
	SYNTAX     Unsigned32
	MAX-ACCESS read-only
	STATUS     current
	DESCRIPTION 
		"This parameter represents the authentication alogorithm used for the station."
	::= { wirelessIfStaStatsTableEntry 44 }

wirelessIfStaStatsAssociationID  OBJECT-TYPE
	SYNTAX     Unsigned32
	MAX-ACCESS read-only
	STATUS     current
	DESCRIPTION 
		"This parameter represents the association ID of the station."
	::= { wirelessIfStaStatsTableEntry 45 }

wirelessIfStaStatsVlanTag  OBJECT-TYPE
	SYNTAX     Unsigned32
	MAX-ACCESS read-only
	STATUS     current
	DESCRIPTION 
		"This parameter represents the VLAN tag of the station."
	::= { wirelessIfStaStatsTableEntry 46 }

wirelessIfStaStatsAssocationTime  OBJECT-TYPE
	SYNTAX     Unsigned32
	MAX-ACCESS read-only
	STATUS     current
	DESCRIPTION 
		"This parameter represents the association time of the station."
	::= { wirelessIfStaStatsTableEntry 47 }

wirelessIfStaStatsTxPower  OBJECT-TYPE
	SYNTAX     Unsigned32
	MAX-ACCESS read-only
	STATUS     current
	DESCRIPTION 
		"This parameter represents the transmission power of the station."
	::= { wirelessIfStaStatsTableEntry 48 }

wirelessIfStaStatsInactivityTimer  OBJECT-TYPE
	SYNTAX     Unsigned32
	MAX-ACCESS read-only
	STATUS     current
	DESCRIPTION 
		"This parameter represents the inactivity time of the station."
	::= { wirelessIfStaStatsTableEntry 49 }

wirelessIfStaStatsStationOperatingMode  OBJECT-TYPE
	SYNTAX     Unsigned32
	MAX-ACCESS read-only
	STATUS     current
	DESCRIPTION 
		"This parameter represents the wireless operating mode of station."
	::= { wirelessIfStaStatsTableEntry 50 }

wirelessIfStaStatsHTCapability  OBJECT-TYPE
	SYNTAX     Unsigned32
	MAX-ACCESS read-only
	STATUS     current
	DESCRIPTION 
		"This parameter represents the HT (high throughput) capability in 11n mode."
	::= { wirelessIfStaStatsTableEntry 51 }

-- ======================================================================================
-- Definition of the Wireless Interface WORP Station Statistics Subgroup objects : wirelessIfStaStats
-- ======================================================================================
-- Wireless Interface WORP Station Statistics Table

wirelessIfWORPStaStatsTable  OBJECT-TYPE
	SYNTAX SEQUENCE OF WirelessIfWORPStaStatsTableEntry
	MAX-ACCESS not-accessible
	STATUS     current
	DESCRIPTION 
		"This table contains WORP stations statistics."
	::= { wirelessIfStaStats 2 }

wirelessIfWORPStaStatsTableEntry  OBJECT-TYPE
	SYNTAX 	WirelessIfWORPStaStatsTableEntry
	MAX-ACCESS not-accessible
	STATUS     current
	DESCRIPTION 
		"This parameter represents an entry in the WORP Interface
		    Satellite Statistics Table."
	INDEX { wirelessIfWORPStaStatsTableIndex }
	::= { wirelessIfWORPStaStatsTable 1 }

WirelessIfWORPStaStatsTableEntry ::= SEQUENCE {
	wirelessIfWORPStaStatsTableIndex
		Unsigned32,
	wirelessIfWORPStaStatsMacAddress
		MacAddress,
	wirelessIfWORPStaStatsSatelliteName
		DisplayString,
	wirelessIfWORPStaStatsAverageLocalSignal
		Integer32,
	wirelessIfWORPStaStatsAverageLocalNoise
		Integer32,
	wirelessIfWORPStaStatsAverageRemoteSignal
		Integer32,
	wirelessIfWORPStaStatsAverageRemoteNoise
		Integer32,
	wirelessIfWORPStaStatsRequestForService
		Counter32,
	wirelessIfWORPStaStatsPollData
		Counter32,
	wirelessIfWORPStaStatsPollNoData
		Counter32,
	wirelessIfWORPStaStatsReplyData
		Counter32,
	wirelessIfWORPStaStatsReplyNoData
		Counter32,
	wirelessIfWORPStaStatsSendSuccess
		Counter32,
	wirelessIfWORPStaStatsSendRetries
		Counter32,
	wirelessIfWORPStaStatsSendFailures
		Counter32,
	wirelessIfWORPStaStatsReceiveSuccess
		Counter32,
	wirelessIfWORPStaStatsReceiveRetries
		Counter32,
	wirelessIfWORPStaStatsReceiveFailures
		Counter32,
	wirelessIfWORPStaStatsPollNoReplies
		Counter32,
	wirelessIfWORPStaStatsLocalTxRate
		Unsigned32,
	wirelessIfWORPStaStatsRemoteTxRate
		Unsigned32,
	wirelessIfWORPStaBridgePort
		Unsigned32,
	wirelessIfWORPStaStatsAverageLocalSNR
		Unsigned32,
	wirelessIfWORPStaStatsAverageRemoteSNR
		Unsigned32,
	wirelessIfWORPStaStatsLocalMimoCtrlSig1
		Integer32,
	wirelessIfWORPStaStatsLocalMimoCtrlSig2
		Integer32,
	wirelessIfWORPStaStatsLocalMimoCtrlSig3
		Integer32,
	wirelessIfWORPStaStatsLocalMimoNoise
		Integer32,
	wirelessIfWORPStaStatsLocalMimoCtrlSNR1
		Unsigned32,
	wirelessIfWORPStaStatsLocalMimoCtrlSNR2
		Unsigned32,
	wirelessIfWORPStaStatsLocalMimoCtrlSNR3
		Unsigned32,
	wirelessIfWORPStaStatsRemoteMimoCtrlSig1
		Integer32,
	wirelessIfWORPStaStatsRemoteMimoCtrlSig2
		Integer32,
	wirelessIfWORPStaStatsRemoteMimoCtrlSig3
		Integer32,
	wirelessIfWORPStaStatsRemoteMimoNoise
		Integer32,
	wirelessIfWORPStaStatsRemoteMimoCtrlSNR1
		Unsigned32,
	wirelessIfWORPStaStatsRemoteMimoCtrlSNR2
		Unsigned32,
	wirelessIfWORPStaStatsRemoteMimoCtrlSNR3
		Unsigned32,
	wirelessIfWORPStaStatsLocalChainBalStatus
		INTEGER,
	wirelessIfWORPStaStatsRemoteChainBalStatus
		INTEGER,
	wirelessIfWORPStaStatsLocalMimoNoise1
		Integer32,
	wirelessIfWORPStaStatsLocalMimoNoise2
		Integer32,
	wirelessIfWORPStaStatsLocalMimoNoise3
		Integer32,
	wirelessIfWORPStaStatsRemoteMimoNoise1
		Integer32,
	wirelessIfWORPStaStatsRemoteMimoNoise2
		Integer32,
	wirelessIfWORPStaStatsRemoteMimoNoise3
		Integer32,
	wirelessIfWORPStaStatsRemoteWORPVersion
		Unsigned32,
	wirelessIfWORPStaStatsActiveTPC
		Unsigned32,
	wirelessIfWORPStaStatsActiveEIRP
		Unsigned32,
	wirelessIfWORPStaStatsActivePower
		Unsigned32,
	wirelessIfWORPStaStatsStationDisconnect
		Integer32,
	wirelessIfWORPStaPort
		Unsigned32,
	wirelessIfWORPStaStatsSupportedRates
		OCTET STRING,
	wirelessIfWORPStaStatsMinSNRInfo
		OCTET STRING,
	wirelessIfWORPStaStatsMaxSNRInfo
		OCTET STRING,
	wirelessIfWORPStaStatsOperationalMode
		INTEGER,
	wirelessIfWORPStaStatsGuardInterval
		INTEGER,
	wirelessIfWORPStaStatsLinkProfileIndex
		Unsigned32,
	wirelessIfWORPStaStatsQoSClassIndex
		Unsigned32,
	wirelessIfWORPStaStatsDCSReTxPercentage
		Integer32,
	wirelessIfWORPStaStatsTxAntennas
		INTEGER,
        wirelessIfWORPStaStatsSatelliteIP
            IpAddress
	}

wirelessIfWORPStaStatsTableIndex  OBJECT-TYPE
	SYNTAX     Unsigned32
	MAX-ACCESS read-only
	STATUS     current
	DESCRIPTION 
		"This parameter represents the table index for Station Stats Table."
	::= { wirelessIfWORPStaStatsTableEntry 1 }

wirelessIfWORPStaStatsMacAddress  OBJECT-TYPE
	SYNTAX     MacAddress
	MAX-ACCESS read-only
	STATUS     current
	DESCRIPTION 
		"This parameter represents the MAC address of the satellite 
		    for which the statistics are gathered."
	::= { wirelessIfWORPStaStatsTableEntry 2 }

wirelessIfWORPStaStatsSatelliteName  OBJECT-TYPE
	SYNTAX     DisplayString
	MAX-ACCESS read-only
	STATUS     current
	DESCRIPTION 
		"This parameter identifies the name of the base unit being tested with."
	::= { wirelessIfWORPStaStatsTableEntry 3 }

wirelessIfWORPStaStatsAverageLocalSignal  OBJECT-TYPE
	SYNTAX     Integer32 (-102..-10)
	MAX-ACCESS read-only
	STATUS     current
	DESCRIPTION 
		"The current signal level calculated over all inbound packets.
		        This variable indicates the running average of the local signal 
		        level using the algorithm (3/4*oldvalue + 1/4*newvalue)."
	::= { wirelessIfWORPStaStatsTableEntry 4 }

wirelessIfWORPStaStatsAverageLocalNoise  OBJECT-TYPE
	SYNTAX     Integer32 (-102..-10)
	MAX-ACCESS read-only
	STATUS     current
	DESCRIPTION 
		"The current noise level calculated over all inbound packets.
		        This variable indicates the running average of the local noise 
		        level using the algorithm (3/4*oldvalue + 1/4*newvalue)."
	::= { wirelessIfWORPStaStatsTableEntry 5 }

wirelessIfWORPStaStatsAverageRemoteSignal  OBJECT-TYPE
	SYNTAX     Integer32 (-102..-10)
	MAX-ACCESS read-only
	STATUS     current
	DESCRIPTION 
		"The current remote signal level calculated over the inbound 
		        packets send by this station.  This variable indicates the 
		        running average over all registered stations of the remote 
		        signal level using the algorithm (3/4*oldvalue + 1/4*newvalue)."
	::= { wirelessIfWORPStaStatsTableEntry 6 }

wirelessIfWORPStaStatsAverageRemoteNoise  OBJECT-TYPE
	SYNTAX     Integer32 (-102..-10)
	MAX-ACCESS read-only
	STATUS     current
	DESCRIPTION 
		"The current average remote noise level calculated over the 
		        inbound packets send by this station.  This variable indicates 
		        the running average over all registered stations of the remote 
		        noise level using the algorithm (3/4*oldvalue + 1/4*newvalue)."
	::= { wirelessIfWORPStaStatsTableEntry 7 }

wirelessIfWORPStaStatsRequestForService  OBJECT-TYPE
	SYNTAX     Counter32
	MAX-ACCESS read-only
	STATUS     current
	DESCRIPTION 
		"The number of requests for service sent (satellite) or 
		        received (base)."
	::= { wirelessIfWORPStaStatsTableEntry 8 }

wirelessIfWORPStaStatsPollData  OBJECT-TYPE
	SYNTAX     Counter32
	MAX-ACCESS read-only
	STATUS     current
	DESCRIPTION 
		"The number of polls with data sent (base) or received 
		        (satellite)."
	::= { wirelessIfWORPStaStatsTableEntry 9 }

wirelessIfWORPStaStatsPollNoData  OBJECT-TYPE
	SYNTAX     Counter32
	MAX-ACCESS read-only
	STATUS     current
	DESCRIPTION 
		"The number of polls with no data sent (base) or received 
		        (satellite)."
	::= { wirelessIfWORPStaStatsTableEntry 10 }

wirelessIfWORPStaStatsReplyData  OBJECT-TYPE
	SYNTAX     Counter32
	MAX-ACCESS read-only
	STATUS     current
	DESCRIPTION 
		"The number of poll replies with data sent (satellite) or 
		        received (base).  This counter does not include replies with the 
		        MoreData flag set (see ReplyMoreData)."
	::= { wirelessIfWORPStaStatsTableEntry 11 }

wirelessIfWORPStaStatsReplyNoData  OBJECT-TYPE
	SYNTAX     Counter32
	MAX-ACCESS read-only
	STATUS     current
	DESCRIPTION 
		"The number of poll replies with no data sent (satellite) or 
		        received (base)."
	::= { wirelessIfWORPStaStatsTableEntry 12 }

wirelessIfWORPStaStatsSendSuccess  OBJECT-TYPE
	SYNTAX     Counter32
	MAX-ACCESS read-only
	STATUS     current
	DESCRIPTION 
		"The number of data packets sent that were acknowledged and did 
		        not need a retransmit."
	::= { wirelessIfWORPStaStatsTableEntry 13 }

wirelessIfWORPStaStatsSendRetries  OBJECT-TYPE
	SYNTAX     Counter32
	MAX-ACCESS read-only
	STATUS     current
	DESCRIPTION 
		"The number of data packets sent that needed retransmition but 
		        were finally received succesfully by the remote partner."
	::= { wirelessIfWORPStaStatsTableEntry 14 }

wirelessIfWORPStaStatsSendFailures  OBJECT-TYPE
	SYNTAX     Counter32
	MAX-ACCESS read-only
	STATUS     current
	DESCRIPTION 
		"The number of data packets sent that were (finally) not received 
		        succesfully by the remote partner."
	::= { wirelessIfWORPStaStatsTableEntry 15 }

wirelessIfWORPStaStatsReceiveSuccess  OBJECT-TYPE
	SYNTAX     Counter32
	MAX-ACCESS read-only
	STATUS     current
	DESCRIPTION 
		"The number of data packets received that were acknowledged and 
		        did not need a retransmit of the remote partner."
	::= { wirelessIfWORPStaStatsTableEntry 16 }

wirelessIfWORPStaStatsReceiveRetries  OBJECT-TYPE
	SYNTAX     Counter32
	MAX-ACCESS read-only
	STATUS     current
	DESCRIPTION 
		"The number of data packets received that needed retransmition by 
		        the remote partner but were finally received succesfully."
	::= { wirelessIfWORPStaStatsTableEntry 17 }

wirelessIfWORPStaStatsReceiveFailures  OBJECT-TYPE
	SYNTAX     Counter32
	MAX-ACCESS read-only
	STATUS     current
	DESCRIPTION 
		"The number of data packets that were (finally) not received 
		        succesfully."
	::= { wirelessIfWORPStaStatsTableEntry 18 }

wirelessIfWORPStaStatsPollNoReplies  OBJECT-TYPE
	SYNTAX     Counter32
	MAX-ACCESS read-only
	STATUS     current
	DESCRIPTION 
		"The number of times a poll was sent but no reply was received. 
		        This parameter only applies to the base."
	::= { wirelessIfWORPStaStatsTableEntry 19 }

wirelessIfWORPStaStatsLocalTxRate  OBJECT-TYPE
	SYNTAX     Unsigned32
	MAX-ACCESS read-only
	STATUS     current
	DESCRIPTION 
		"This parameter represents the Transmit Data Rate of the BSU."
	::= { wirelessIfWORPStaStatsTableEntry 20 }

wirelessIfWORPStaStatsRemoteTxRate  OBJECT-TYPE
	SYNTAX     Unsigned32
	MAX-ACCESS read-only
	STATUS     current
	DESCRIPTION 
		"This parameter represents the Transmit Data Rate of the SU
		 which is registered to this SU."
	::= { wirelessIfWORPStaStatsTableEntry 21 }

wirelessIfWORPStaBridgePort  OBJECT-TYPE
	SYNTAX     Unsigned32
	MAX-ACCESS read-only
	STATUS     current
	DESCRIPTION 
		"This parameter represents the port number of the bridge for which
		                 this station is connected."
	::= { wirelessIfWORPStaStatsTableEntry 22 }

wirelessIfWORPStaStatsAverageLocalSNR  OBJECT-TYPE
	SYNTAX     Unsigned32
	MAX-ACCESS read-only
	STATUS     current
	DESCRIPTION 
		""
	::= { wirelessIfWORPStaStatsTableEntry 23 }

wirelessIfWORPStaStatsAverageRemoteSNR  OBJECT-TYPE
	SYNTAX     Unsigned32
	MAX-ACCESS read-only
	STATUS     current
	DESCRIPTION 
		""
	::= { wirelessIfWORPStaStatsTableEntry 24 }

wirelessIfWORPStaStatsLocalMimoCtrlSig1  OBJECT-TYPE
	SYNTAX     Integer32
	MAX-ACCESS read-only
	STATUS     current
	DESCRIPTION 
		""
	::= { wirelessIfWORPStaStatsTableEntry 25 }

wirelessIfWORPStaStatsLocalMimoCtrlSig2  OBJECT-TYPE
	SYNTAX     Integer32
	MAX-ACCESS read-only
	STATUS     current
	DESCRIPTION 
		""
	::= { wirelessIfWORPStaStatsTableEntry 26 }

wirelessIfWORPStaStatsLocalMimoCtrlSig3  OBJECT-TYPE
	SYNTAX     Integer32
	MAX-ACCESS read-only
	STATUS     current
	DESCRIPTION 
		""
	::= { wirelessIfWORPStaStatsTableEntry 27 }

wirelessIfWORPStaStatsLocalMimoNoise  OBJECT-TYPE
	SYNTAX     Integer32
	MAX-ACCESS read-only
	STATUS     current
	DESCRIPTION 
		""
	::= { wirelessIfWORPStaStatsTableEntry 28 }

wirelessIfWORPStaStatsLocalMimoCtrlSNR1  OBJECT-TYPE
	SYNTAX     Unsigned32
	MAX-ACCESS read-only
	STATUS     current
	DESCRIPTION 
		""
	::= { wirelessIfWORPStaStatsTableEntry 29 }

wirelessIfWORPStaStatsLocalMimoCtrlSNR2  OBJECT-TYPE
	SYNTAX     Unsigned32
	MAX-ACCESS read-only
	STATUS     current
	DESCRIPTION 
		""
	::= { wirelessIfWORPStaStatsTableEntry 30 }

wirelessIfWORPStaStatsLocalMimoCtrlSNR3  OBJECT-TYPE
	SYNTAX     Unsigned32
	MAX-ACCESS read-only
	STATUS     current
	DESCRIPTION 
		""
	::= { wirelessIfWORPStaStatsTableEntry 31 }

wirelessIfWORPStaStatsRemoteMimoCtrlSig1  OBJECT-TYPE
	SYNTAX     Integer32
	MAX-ACCESS read-only
	STATUS     current
	DESCRIPTION 
		""
	::= { wirelessIfWORPStaStatsTableEntry 32 }

wirelessIfWORPStaStatsRemoteMimoCtrlSig2  OBJECT-TYPE
	SYNTAX     Integer32
	MAX-ACCESS read-only
	STATUS     current
	DESCRIPTION 
		""
	::= { wirelessIfWORPStaStatsTableEntry 33 }

wirelessIfWORPStaStatsRemoteMimoCtrlSig3  OBJECT-TYPE
	SYNTAX     Integer32
	MAX-ACCESS read-only
	STATUS     current
	DESCRIPTION 
		""
	::= { wirelessIfWORPStaStatsTableEntry 34 }

wirelessIfWORPStaStatsRemoteMimoNoise  OBJECT-TYPE
	SYNTAX     Integer32
	MAX-ACCESS read-only
	STATUS     current
	DESCRIPTION 
		""
	::= { wirelessIfWORPStaStatsTableEntry 35 }

wirelessIfWORPStaStatsRemoteMimoCtrlSNR1  OBJECT-TYPE
	SYNTAX     Unsigned32
	MAX-ACCESS read-only
	STATUS     current
	DESCRIPTION 
		""
	::= { wirelessIfWORPStaStatsTableEntry 36 }

wirelessIfWORPStaStatsRemoteMimoCtrlSNR2  OBJECT-TYPE
	SYNTAX     Unsigned32
	MAX-ACCESS read-only
	STATUS     current
	DESCRIPTION 
		""
	::= { wirelessIfWORPStaStatsTableEntry 37 }

wirelessIfWORPStaStatsRemoteMimoCtrlSNR3  OBJECT-TYPE
	SYNTAX     Unsigned32
	MAX-ACCESS read-only
	STATUS     current
	DESCRIPTION 
		""
	::= { wirelessIfWORPStaStatsTableEntry 38 }

wirelessIfWORPStaStatsLocalChainBalStatus  OBJECT-TYPE
	SYNTAX     INTEGER {
		notApplicable (1),
		balanced (2),
		notBalanced (3)
	}
	MAX-ACCESS read-only
	STATUS     current
	DESCRIPTION 
		"When this parameter indicates the local chain balance status."
	::= { wirelessIfWORPStaStatsTableEntry 39 }

wirelessIfWORPStaStatsRemoteChainBalStatus  OBJECT-TYPE
	SYNTAX     INTEGER {
		notApplicable (1),
		balanced (2),
		notBalanced (3)
	}
	MAX-ACCESS read-only
	STATUS     current
	DESCRIPTION 
		"When this parameter indicates the remote chain balance status."
	::= { wirelessIfWORPStaStatsTableEntry 40 }

wirelessIfWORPStaStatsLocalMimoNoise1  OBJECT-TYPE
	SYNTAX     Integer32
	MAX-ACCESS read-only
	STATUS     current
	DESCRIPTION 
		""
	::= { wirelessIfWORPStaStatsTableEntry 41 }

wirelessIfWORPStaStatsLocalMimoNoise2  OBJECT-TYPE
	SYNTAX     Integer32
	MAX-ACCESS read-only
	STATUS     current
	DESCRIPTION 
		""
	::= { wirelessIfWORPStaStatsTableEntry 42 }

wirelessIfWORPStaStatsLocalMimoNoise3  OBJECT-TYPE
	SYNTAX     Integer32
	MAX-ACCESS read-only
	STATUS     current
	DESCRIPTION 
		""
	::= { wirelessIfWORPStaStatsTableEntry 43 }

wirelessIfWORPStaStatsRemoteMimoNoise1  OBJECT-TYPE
	SYNTAX     Integer32
	MAX-ACCESS read-only
	STATUS     current
	DESCRIPTION 
		""
	::= { wirelessIfWORPStaStatsTableEntry 44 }

wirelessIfWORPStaStatsRemoteMimoNoise2  OBJECT-TYPE
	SYNTAX     Integer32
	MAX-ACCESS read-only
	STATUS     current
	DESCRIPTION 
		""
	::= { wirelessIfWORPStaStatsTableEntry 45 }

wirelessIfWORPStaStatsRemoteMimoNoise3  OBJECT-TYPE
	SYNTAX     Integer32
	MAX-ACCESS read-only
	STATUS     current
	DESCRIPTION 
		""
	::= { wirelessIfWORPStaStatsTableEntry 46 }

wirelessIfWORPStaStatsRemoteWORPVersion  OBJECT-TYPE
	SYNTAX     Unsigned32
	MAX-ACCESS read-only
	STATUS     current
	DESCRIPTION 
		"This parameter represents the Rx rate of BSU."
	::= { wirelessIfWORPStaStatsTableEntry 47 }

wirelessIfWORPStaStatsActiveTPC  OBJECT-TYPE
	SYNTAX     Unsigned32
	MAX-ACCESS read-only
	STATUS     current
	DESCRIPTION 
		"This parameter represents the Current TPC.
		 Obtained value divided by 2 gives the Current TPC."
	::= { wirelessIfWORPStaStatsTableEntry 48 }

wirelessIfWORPStaStatsActiveEIRP  OBJECT-TYPE
	SYNTAX     Unsigned32
	MAX-ACCESS read-only
	STATUS     current
	DESCRIPTION 
		"This parameter represents the Current EIRP.
		 Obtained value divided by 2 gives the Current EIRP."
	::= { wirelessIfWORPStaStatsTableEntry 49 }

wirelessIfWORPStaStatsActivePower  OBJECT-TYPE
	SYNTAX     Unsigned32
	MAX-ACCESS read-only
	STATUS     current
	DESCRIPTION 
		"This parameter represents the Current Power.
		 Obtained value divided by 2 gives the Current Power."
	::= { wirelessIfWORPStaStatsTableEntry 50 }

wirelessIfWORPStaStatsStationDisconnect  OBJECT-TYPE
	SYNTAX     Integer32
	MAX-ACCESS read-write
	STATUS     current
	DESCRIPTION 
		"This parameter is used to disconnect the station."
	::= { wirelessIfWORPStaStatsTableEntry 51 }

wirelessIfWORPStaPort  OBJECT-TYPE
	SYNTAX     Unsigned32
	MAX-ACCESS read-only
	STATUS     current
	DESCRIPTION 
		"This parameter represents the port number of the bridge for which
		                 this station is connected."
	::= { wirelessIfWORPStaStatsTableEntry 52 }

wirelessIfWORPStaStatsSupportedRates  OBJECT-TYPE
	SYNTAX     OCTET STRING
	MAX-ACCESS read-only
	STATUS     current
	DESCRIPTION 
		"This parameter represents the Supported Data Rates of SU."
	::= { wirelessIfWORPStaStatsTableEntry 53 }

wirelessIfWORPStaStatsMinSNRInfo  OBJECT-TYPE
	SYNTAX     OCTET STRING
	MAX-ACCESS read-only
	STATUS     current
	DESCRIPTION 
		"This parameter represents the Minimum SNR Table for this SU."
	::= { wirelessIfWORPStaStatsTableEntry 54 }

wirelessIfWORPStaStatsMaxSNRInfo  OBJECT-TYPE
	SYNTAX     OCTET STRING
	MAX-ACCESS read-only
	STATUS     current
	DESCRIPTION 
		"This parameter represents the Maximum SNR Table for this SU."
	::= { wirelessIfWORPStaStatsTableEntry 55 }

wirelessIfWORPStaStatsOperationalMode  OBJECT-TYPE
	SYNTAX     INTEGER {
		highThroughput (1),
		legacy (2)
	}
	MAX-ACCESS read-only
	STATUS     current
	DESCRIPTION 
		"This parameter represents the device operation mode."
	::= { wirelessIfWORPStaStatsTableEntry 56 }

wirelessIfWORPStaStatsGuardInterval  OBJECT-TYPE
	SYNTAX     INTEGER {
		shortGI-400nSec (1),
		fullGI-800nSec (2)
	}
	MAX-ACCESS read-only
	STATUS     current
	DESCRIPTION 
		"This parameter represents the device Guard Interval."
	::= { wirelessIfWORPStaStatsTableEntry 57 }

wirelessIfWORPStaStatsLinkProfileIndex  OBJECT-TYPE
	SYNTAX     Unsigned32
	MAX-ACCESS read-only
	STATUS     current
	DESCRIPTION 
		"This parameter represents the link profile index for this SU."
	::= { wirelessIfWORPStaStatsTableEntry 58 }

wirelessIfWORPStaStatsQoSClassIndex  OBJECT-TYPE
	SYNTAX     Unsigned32
	MAX-ACCESS read-only
	STATUS     current
	DESCRIPTION 
		"This parameter represents the qos class index for this SU."
	::= { wirelessIfWORPStaStatsTableEntry 59 }

wirelessIfWORPStaStatsDCSReTxPercentage  OBJECT-TYPE
	SYNTAX     Integer32 (0..100)
	MAX-ACCESS read-only
	STATUS     current
	DESCRIPTION 
		"This parameter represents the ReTransmission Percentage for this SU."
	::= { wirelessIfWORPStaStatsTableEntry 60 }

wirelessIfWORPStaStatsTxAntennas  OBJECT-TYPE
	SYNTAX     INTEGER {
		one (1),
		two (2),
		three (3),
		four (4),
		five (5),
		six (6),
		seven (7)
	}
	MAX-ACCESS read-only
	STATUS     current
	DESCRIPTION 
		"This parameter represents the Tx Antenna chain mask. This is represented as bitmask.
		         Eg: 3 - 011 (binary value) - first and second antennas are enabled. 
		             7 - 111 (binary value) - all three are enabled."
	::= { wirelessIfWORPStaStatsTableEntry 61 }

wirelessIfWORPStaStatsSatelliteIP OBJECT-TYPE
    SYNTAX      IpAddress
    MAX-ACCESS  read-only
    STATUS      current
    DESCRIPTION "This parameter represents the IP address of the satellite 
            for which the statistics are gathered."
    ::= {wirelessIfWORPStaStatsTableEntry 62 }

wirelessIfMonNumOfStaConnected  OBJECT-TYPE
	SYNTAX     Unsigned32
	MAX-ACCESS read-only
	STATUS     current
	DESCRIPTION 
		"This parameter represents the number of stations connected."
	::= { wirelessIfStaStats 3 }

-- ======================================================================================
-- Definition of the Wireless Interface WORP Monitoring Group objects : wirelessIfWORPStatss
-- ======================================================================================
-- ======================================================================================
-- Definition of the Wireless Interface WORP Statistics Subgroup objects : wirelessIfWORPStatss
-- ======================================================================================
-- Wireless Interface WORP Statistics Table

wirelessIfWORPStatsTable  OBJECT-TYPE
	SYNTAX SEQUENCE OF WirelessIfWORPStatsTableEntry
	MAX-ACCESS not-accessible
	STATUS     current
	DESCRIPTION 
		"This table is used to monitor the statistics of interfaces that 
		    run WORP."
	::= { wirelessIfWORPStats 1 }

wirelessIfWORPStatsTableEntry  OBJECT-TYPE
	SYNTAX 	WirelessIfWORPStatsTableEntry
	MAX-ACCESS not-accessible
	STATUS     current
	DESCRIPTION 
		"This parameter represents an entry in the WORP Interface
		    Statistics Table."
	INDEX { wirelessIfWORPStatsTableIndex }
	::= { wirelessIfWORPStatsTable 1 }

WirelessIfWORPStatsTableEntry ::= SEQUENCE {
	wirelessIfWORPStatsTableIndex
		Unsigned32,
	wirelessIfWORPStatsAverageLocalSignal
		Integer32,
	wirelessIfWORPStatsAverageLocalNoise
		Integer32,
	wirelessIfWORPStatsAverageRemoteSignal
		Integer32,
	wirelessIfWORPStatsAverageRemoteNoise
		Integer32,
	wirelessIfWORPStatsRemotePartners
		Unsigned32,
	wirelessIfWORPStatsBaseStationAnnounces
		Counter32,
	wirelessIfWORPStatsRequestForService
		Counter32,
	wirelessIfWORPStatsRegistrationRequests
		Counter32,
	wirelessIfWORPStatsRegistrationRejects
		Counter32,
	wirelessIfWORPStatsAuthenticationRequests
		Counter32,
	wirelessIfWORPStatsAuthenticationConfirms
		Counter32,
	wirelessIfWORPStatsRegistrationAttempts
		Counter32,
	wirelessIfWORPStatsRegistrationIncompletes
		Counter32,
	wirelessIfWORPStatsRegistrationTimeouts
		Counter32,
	wirelessIfWORPStatsRegistrationLastReason
		INTEGER,
	wirelessIfWORPStatsPollData
		Counter32,
	wirelessIfWORPStatsPollNoData
		Counter32,
	wirelessIfWORPStatsReplyData
		Counter32,
	wirelessIfWORPStatsReplyMoreData
		Counter32,
	wirelessIfWORPStatsReplyNoData
		Counter32,
	wirelessIfWORPStatsPollNoReplies
		Counter32,
	wirelessIfWORPStatsSendSuccess
		Counter32,
	wirelessIfWORPStatsSendRetries
		Counter32,
	wirelessIfWORPStatsSendFailures
		Counter32,
	wirelessIfWORPStatsReceiveSuccess
		Counter32,
	wirelessIfWORPStatsReceiveRetries
		Counter32,
	wirelessIfWORPStatsReceiveFailures
		Counter32,
	wirelessIfWORPStatsProvisionedUplinkCIR
		Unsigned32,
	wirelessIfWORPStatsProvisionedDownlinkCIR
		Unsigned32,
	wirelessIfWORPStatsProvisionedUplinkMIR
		Unsigned32,
	wirelessIfWORPStatsProvisionedDownlinkMIR
		Unsigned32,
	wirelessIfWORPStatsActiveUplinkCIR
		Unsigned32,
	wirelessIfWORPStatsActiveDownlinkCIR
		Unsigned32,
	wirelessIfWORPStatsActiveUplinkMIR
		Unsigned32,
	wirelessIfWORPStatsActiveDownlinkMIR
		Unsigned32,
	wirelessIfWORPStatsCurrentUplinkBandwidth
		Unsigned32,
	wirelessIfWORPStatsCurrentDownlinkBandwidth
		Unsigned32,
	wirelessIfWORPStatsWORPVersion
		Unsigned32,
	wirelessIfWORPStatsAnnounceTxRate
		Unsigned32,
	wirelessIfWORPStatsAnnounceDataStream
		INTEGER,
	wirelessIfWORPStatsAnnounceTPC
		Unsigned32,
	wirelessIfWORPStatsAnnounceTxEIRP
		Unsigned32,
	wirelessIfWORPStatsAnnounceTxPower
		Unsigned32,
	wirelessIfWORPStatsAnnounceTxChainMask
		INTEGER,
	wirelessIfWORPStatsBcastTxRate
		Unsigned32,
	wirelessIfWORPStatsBcastDataStream
		INTEGER,
	wirelessIfWORPStatsBcastTPC
		Unsigned32,
	wirelessIfWORPStatsBcastTxEIRP
		Unsigned32,
	wirelessIfWORPStatsBcastTxPower
		Unsigned32,
	wirelessIfWORPStatsBcastTxChainMask
		INTEGER,
	wirelessIfWORPStatsPollAutoReplies
		Counter32,
	wirelessIfWORPStatsDownlinkBE
		Unsigned32
}

wirelessIfWORPStatsTableIndex  OBJECT-TYPE
	SYNTAX     Unsigned32
	MAX-ACCESS read-only
	STATUS     current
	DESCRIPTION 
		"This parameter represents the radio interface for which the WORP statistics
		         are gathered and index to the wirelessIfWORPStats table."
	::= { wirelessIfWORPStatsTableEntry 1 }

-- =======================
-- Signal Statistics Group
-- =======================

wirelessIfWORPStatsAverageLocalSignal  OBJECT-TYPE
	SYNTAX     Integer32 (-102..-10)
	MAX-ACCESS read-only
	STATUS     current
	DESCRIPTION 
		"This parameter displays the current signal level calculated over all inbound 
		         packets."
	::= { wirelessIfWORPStatsTableEntry 2 }

wirelessIfWORPStatsAverageLocalNoise  OBJECT-TYPE
	SYNTAX     Integer32 (-102..-10)
	MAX-ACCESS read-only
	STATUS     current
	DESCRIPTION 
		"This parameter displays the current noise level calculated over all inbound packets."
	::= { wirelessIfWORPStatsTableEntry 3 }

wirelessIfWORPStatsAverageRemoteSignal  OBJECT-TYPE
	SYNTAX     Integer32 (-102..-10)
	MAX-ACCESS read-only
	STATUS     current
	DESCRIPTION 
		"This parameter displays the current signal level calculated over the inbound packets 
		         received at the peer end."
	::= { wirelessIfWORPStatsTableEntry 4 }

wirelessIfWORPStatsAverageRemoteNoise  OBJECT-TYPE
	SYNTAX     Integer32 (-102..-10)
	MAX-ACCESS read-only
	STATUS     current
	DESCRIPTION 
		"This parameter displays the current noise level calculated over the inbound packets 
		         received at the peer end."
	::= { wirelessIfWORPStatsTableEntry 5 }

-- ==============================
-- Registration Statistics Group
-- ==============================

wirelessIfWORPStatsRemotePartners  OBJECT-TYPE
	SYNTAX     Unsigned32
	MAX-ACCESS read-only
	STATUS     current
	DESCRIPTION 
		"This parameter displays the number of remote partners. For a satellite, this parameter
		         will always be zero or one."
	::= { wirelessIfWORPStatsTableEntry 6 }

wirelessIfWORPStatsBaseStationAnnounces  OBJECT-TYPE
	SYNTAX     Counter32
	MAX-ACCESS read-only
	STATUS     current
	DESCRIPTION 
		"This parameter displays the number of Announcement messages sent (base) or received 
		         (satellite) on WORP interface"
	::= { wirelessIfWORPStatsTableEntry 7 }

wirelessIfWORPStatsRequestForService  OBJECT-TYPE
	SYNTAX     Counter32
	MAX-ACCESS read-only
	STATUS     current
	DESCRIPTION 
		"This parameter displays the number of requests for service messages sent (satellite) 
		         or received (base)."
	::= { wirelessIfWORPStatsTableEntry 8 }

wirelessIfWORPStatsRegistrationRequests  OBJECT-TYPE
	SYNTAX     Counter32
	MAX-ACCESS read-only
	STATUS     current
	DESCRIPTION 
		"This parameter displays the number of registration request messages sent (satellite) 
		         or received (base) on  WORP interface."
	::= { wirelessIfWORPStatsTableEntry 9 }

wirelessIfWORPStatsRegistrationRejects  OBJECT-TYPE
	SYNTAX     Counter32
	MAX-ACCESS read-only
	STATUS     current
	DESCRIPTION 
		"This parameter displays the number of times registration attempts were rejected."
	::= { wirelessIfWORPStatsTableEntry 10 }

wirelessIfWORPStatsAuthenticationRequests  OBJECT-TYPE
	SYNTAX     Counter32
	MAX-ACCESS read-only
	STATUS     current
	DESCRIPTION 
		"This parameter displays  the number of authentication request messages sent 
		         (satellite) or received (base) on WORP interface."
	::= { wirelessIfWORPStatsTableEntry 11 }

wirelessIfWORPStatsAuthenticationConfirms  OBJECT-TYPE
	SYNTAX     Counter32
	MAX-ACCESS read-only
	STATUS     current
	DESCRIPTION 
		"This parameter displays the number of authentication confirm messages  sent
		         (base) or received (satellite) on WORP interface."
	::= { wirelessIfWORPStatsTableEntry 12 }

wirelessIfWORPStatsRegistrationAttempts  OBJECT-TYPE
	SYNTAX     Counter32
	MAX-ACCESS read-only
	STATUS     current
	DESCRIPTION 
		"This parameter represents the number of times a Registration Attempt has been 
		         initiated."
	::= { wirelessIfWORPStatsTableEntry 13 }

wirelessIfWORPStatsRegistrationIncompletes  OBJECT-TYPE
	SYNTAX     Counter32
	MAX-ACCESS read-only
	STATUS     current
	DESCRIPTION 
		"This parameter represents the number of registration attempts that is not 
		         completed yet. "
	::= { wirelessIfWORPStatsTableEntry 14 }

wirelessIfWORPStatsRegistrationTimeouts  OBJECT-TYPE
	SYNTAX     Counter32
	MAX-ACCESS read-only
	STATUS     current
	DESCRIPTION 
		"This parameter represents the number of times the registration procedure
		         timed out."
	::= { wirelessIfWORPStatsTableEntry 15 }

wirelessIfWORPStatsRegistrationLastReason  OBJECT-TYPE
	SYNTAX     INTEGER {
		none (1),
		noMoreAllowed (2),
		incorrectParameter (3),
		roaming (4),
		timeout (5),
		lowQuality (6),
		localTerminated (7),
		remoteTerminated (8),
		radarDetected (9),
		dcs (10),
		linkInactive (11)
	}
	MAX-ACCESS read-only
	STATUS     current
	DESCRIPTION 
		"This parameter represents the reason for why the last registration was aborted
		         or failed."
	::= { wirelessIfWORPStatsTableEntry 16 }

-- ==================================
-- WORP Data Message Statistics Group
-- ==================================

wirelessIfWORPStatsPollData  OBJECT-TYPE
	SYNTAX     Counter32
	MAX-ACCESS read-only
	STATUS     current
	DESCRIPTION 
		"This parameter represents the number of polls with data messages sent 
		         (base) or received (satellite). "
	::= { wirelessIfWORPStatsTableEntry 17 }

wirelessIfWORPStatsPollNoData  OBJECT-TYPE
	SYNTAX     Counter32
	MAX-ACCESS read-only
	STATUS     current
	DESCRIPTION 
		"This parameter represents the number of polls with no data messages  sent 
		         (base) or received (satellite).      "
	::= { wirelessIfWORPStatsTableEntry 18 }

wirelessIfWORPStatsReplyData  OBJECT-TYPE
	SYNTAX     Counter32
	MAX-ACCESS read-only
	STATUS     current
	DESCRIPTION 
		"This parameter represents the number of poll replies with data
		         messages sent (satellite) or received (base)."
	::= { wirelessIfWORPStatsTableEntry 19 }

wirelessIfWORPStatsReplyMoreData  OBJECT-TYPE
	SYNTAX     Counter32
	MAX-ACCESS read-only
	STATUS     current
	DESCRIPTION 
		"This parameter represents the number of poll replies with more data messages sent 
		        (satellite) or received (base)."
	::= { wirelessIfWORPStatsTableEntry 20 }

wirelessIfWORPStatsReplyNoData  OBJECT-TYPE
	SYNTAX     Counter32
	MAX-ACCESS read-only
	STATUS     current
	DESCRIPTION 
		"This parameter represents the number of poll replies with no data messages sent
		        (satellite) or received (base)."
	::= { wirelessIfWORPStatsTableEntry 21 }

wirelessIfWORPStatsPollNoReplies  OBJECT-TYPE
	SYNTAX     Counter32
	MAX-ACCESS read-only
	STATUS     current
	DESCRIPTION 
		"This parameter represents the number of times a poll messages were sent but no 
		         reply was received. The parameter in valid only on BSU."
	::= { wirelessIfWORPStatsTableEntry 22 }

-- ==================================
-- Data Transmission Statistics Group
-- ==================================

wirelessIfWORPStatsSendSuccess  OBJECT-TYPE
	SYNTAX     Counter32
	MAX-ACCESS read-only
	STATUS     current
	DESCRIPTION 
		"This parameter displays  the number of data messages sent and acknowledged
		         by the peer successfully."
	::= { wirelessIfWORPStatsTableEntry 23 }

wirelessIfWORPStatsSendRetries  OBJECT-TYPE
	SYNTAX     Counter32
	MAX-ACCESS read-only
	STATUS     current
	DESCRIPTION 
		"This parameter displays  the number of data messages  that are re-transmitted
		         and acknowledged by the peer successfully."
	::= { wirelessIfWORPStatsTableEntry 24 }

wirelessIfWORPStatsSendFailures  OBJECT-TYPE
	SYNTAX     Counter32
	MAX-ACCESS read-only
	STATUS     current
	DESCRIPTION 
		"This parameter displays the number of data messages that requires re-transmission.
		         These frames are not acknowledged by the peer."
	::= { wirelessIfWORPStatsTableEntry 25 }

wirelessIfWORPStatsReceiveSuccess  OBJECT-TYPE
	SYNTAX     Counter32
	MAX-ACCESS read-only
	STATUS     current
	DESCRIPTION 
		"This parameter displays  the number of data messages received and acknowledged
		         successfully."
	::= { wirelessIfWORPStatsTableEntry 26 }

wirelessIfWORPStatsReceiveRetries  OBJECT-TYPE
	SYNTAX     Counter32
	MAX-ACCESS read-only
	STATUS     current
	DESCRIPTION 
		"This parameter displays the number of successfully received re-transmitted data
		         messages."
	::= { wirelessIfWORPStatsTableEntry 27 }

wirelessIfWORPStatsReceiveFailures  OBJECT-TYPE
	SYNTAX     Counter32
	MAX-ACCESS read-only
	STATUS     current
	DESCRIPTION 
		"This parameter displays the number of data messages that were not received 
		         successfully."
	::= { wirelessIfWORPStatsTableEntry 28 }

-- ==============================
-- QoS Bandwidth Statistics Group
-- ==============================

wirelessIfWORPStatsProvisionedUplinkCIR  OBJECT-TYPE
	SYNTAX     Unsigned32
	MAX-ACCESS read-only
	STATUS     current
	DESCRIPTION 
		"This parameter provides information about the total assigned (provisioned) 
		         uplink Committed Information Rate(CIR) including all SUs."
	::= { wirelessIfWORPStatsTableEntry 29 }

wirelessIfWORPStatsProvisionedDownlinkCIR  OBJECT-TYPE
	SYNTAX     Unsigned32
	MAX-ACCESS read-only
	STATUS     current
	DESCRIPTION 
		"This parameter provides information about the total assigned (provisioned) 
		         downlink Commtied Information Rate(CIR) including all SUs."
	::= { wirelessIfWORPStatsTableEntry 30 }

wirelessIfWORPStatsProvisionedUplinkMIR  OBJECT-TYPE
	SYNTAX     Unsigned32
	MAX-ACCESS read-only
	STATUS     current
	DESCRIPTION 
		"This parameter provides information about the total assigned (provisioned) 
		         uplink Maximum Information Rate(MIR) including all SUs."
	::= { wirelessIfWORPStatsTableEntry 31 }

wirelessIfWORPStatsProvisionedDownlinkMIR  OBJECT-TYPE
	SYNTAX     Unsigned32
	MAX-ACCESS read-only
	STATUS     current
	DESCRIPTION 
		"This parameter provides information about the total assigned (provisioned) downlink
		         Maximum Information Rate(MIR) including all SUs."
	::= { wirelessIfWORPStatsTableEntry 32 }

wirelessIfWORPStatsActiveUplinkCIR  OBJECT-TYPE
	SYNTAX     Unsigned32
	MAX-ACCESS read-only
	STATUS     current
	DESCRIPTION 
		"This parameter provides information about the total active uplink Committed Information Rate(CIR)."
	::= { wirelessIfWORPStatsTableEntry 33 }

wirelessIfWORPStatsActiveDownlinkCIR  OBJECT-TYPE
	SYNTAX     Unsigned32
	MAX-ACCESS read-only
	STATUS     current
	DESCRIPTION 
		"This parameter provides information about the total active downlink Committed Information Rate(CIR)."
	::= { wirelessIfWORPStatsTableEntry 34 }

wirelessIfWORPStatsActiveUplinkMIR  OBJECT-TYPE
	SYNTAX     Unsigned32
	MAX-ACCESS read-only
	STATUS     current
	DESCRIPTION 
		"This parameter provides information about the total active uplink Maximum Information Rate(MIR)."
	::= { wirelessIfWORPStatsTableEntry 35 }

wirelessIfWORPStatsActiveDownlinkMIR  OBJECT-TYPE
	SYNTAX     Unsigned32
	MAX-ACCESS read-only
	STATUS     current
	DESCRIPTION 
		"This parameter provides information about the total active downlink Maximum Information Rate(MIR)."
	::= { wirelessIfWORPStatsTableEntry 36 }

wirelessIfWORPStatsCurrentUplinkBandwidth  OBJECT-TYPE
	SYNTAX     Unsigned32
	MAX-ACCESS read-only
	STATUS     current
	DESCRIPTION 
		"This parameter provides information about the current bandwidth utilization on the  uplink direction."
	::= { wirelessIfWORPStatsTableEntry 37 }

wirelessIfWORPStatsCurrentDownlinkBandwidth  OBJECT-TYPE
	SYNTAX     Unsigned32
	MAX-ACCESS read-only
	STATUS     current
	DESCRIPTION 
		"This parameter provides information about the current bandwidth utilization on the  downlink direction."
	::= { wirelessIfWORPStatsTableEntry 38 }

wirelessIfWORPStatsWORPVersion  OBJECT-TYPE
	SYNTAX     Unsigned32
	MAX-ACCESS read-only
	STATUS     current
	DESCRIPTION 
		"This parameter provides the information about the current 
		WORP protocol version."
	::= { wirelessIfWORPStatsTableEntry 39 }

-- ==============================
-- WORP Profile Statistics Group
-- ==============================

wirelessIfWORPStatsAnnounceTxRate  OBJECT-TYPE
	SYNTAX     Unsigned32
	MAX-ACCESS read-only
	STATUS     current
	DESCRIPTION 
		"This parameter provides the Announce Tx Rate of the last packet."
	::= { wirelessIfWORPStatsTableEntry 40 }

wirelessIfWORPStatsAnnounceDataStream  OBJECT-TYPE
	SYNTAX     INTEGER {
		single (1),
		dual (2),
		auto (3)
	}
	MAX-ACCESS read-only
	STATUS     current
	DESCRIPTION 
		"This parameter provides the Announce data stream of the last packet."
	::= { wirelessIfWORPStatsTableEntry 41 }

wirelessIfWORPStatsAnnounceTPC  OBJECT-TYPE
	SYNTAX     Unsigned32
	MAX-ACCESS read-only
	STATUS     current
	DESCRIPTION 
		"This parameter provides Announce TPC of the last packet.
		 Obtained value divided by 2 gives the TPC."
	::= { wirelessIfWORPStatsTableEntry 42 }

wirelessIfWORPStatsAnnounceTxEIRP  OBJECT-TYPE
	SYNTAX     Unsigned32
	MAX-ACCESS read-only
	STATUS     current
	DESCRIPTION 
		"This parameter provides Announce EIRP of the last packet.
		 Obtained value divided by 2 gives the EIRP."
	::= { wirelessIfWORPStatsTableEntry 43 }

wirelessIfWORPStatsAnnounceTxPower  OBJECT-TYPE
	SYNTAX     Unsigned32
	MAX-ACCESS read-only
	STATUS     current
	DESCRIPTION 
		"This parameter provides Announce power of the last packet.
		 Obtained value divided by 2 gives the Power."
	::= { wirelessIfWORPStatsTableEntry 44 }

wirelessIfWORPStatsAnnounceTxChainMask  OBJECT-TYPE
	SYNTAX     INTEGER {
		one (1),
		two (2),
		three (3),
		four (4),
		five (5),
		six (6),
		seven (7)
	}
	MAX-ACCESS read-only
	STATUS     current
	DESCRIPTION 
		"This parameter provides Announce Tx Chain Mask of the last packet."
	::= { wirelessIfWORPStatsTableEntry 45 }

wirelessIfWORPStatsBcastTxRate  OBJECT-TYPE
	SYNTAX     Unsigned32
	MAX-ACCESS read-only
	STATUS     current
	DESCRIPTION 
		"This parameter provides Broadcast Tx rate of the last packet."
	::= { wirelessIfWORPStatsTableEntry 46 }

wirelessIfWORPStatsBcastDataStream  OBJECT-TYPE
	SYNTAX     INTEGER {
		single (1),
		dual (2),
		auto (3)
	}
	MAX-ACCESS read-only
	STATUS     current
	DESCRIPTION 
		"This parameter provides Broadcast data sream of the last packet."
	::= { wirelessIfWORPStatsTableEntry 47 }

wirelessIfWORPStatsBcastTPC  OBJECT-TYPE
	SYNTAX     Unsigned32
	MAX-ACCESS read-only
	STATUS     current
	DESCRIPTION 
		"This parameter provides Broadcast TPC of the last packet.
		 Obtained value divided by 2 gives the TPC."
	::= { wirelessIfWORPStatsTableEntry 48 }

wirelessIfWORPStatsBcastTxEIRP  OBJECT-TYPE
	SYNTAX     Unsigned32
	MAX-ACCESS read-only
	STATUS     current
	DESCRIPTION 
		"This parameter provides Broadcast EIRP of the last packet.
		 Obtained value divided by 2 gives the EIRP."
	::= { wirelessIfWORPStatsTableEntry 49 }

wirelessIfWORPStatsBcastTxPower  OBJECT-TYPE
	SYNTAX     Unsigned32
	MAX-ACCESS read-only
	STATUS     current
	DESCRIPTION 
		"This parameter provides Broadcast Tx power of the last packet.
		 Obtained value divided by 2 gives the Power."
	::= { wirelessIfWORPStatsTableEntry 50 }

wirelessIfWORPStatsBcastTxChainMask  OBJECT-TYPE
	SYNTAX     INTEGER {
		one (1),
		two (2),
		three (3),
		four (4),
		five (5),
		six (6),
		seven (7)
	}
	MAX-ACCESS read-only
	STATUS     current
	DESCRIPTION 
		"This parameter provides Broadcast Tx Chain Mask of the last packet."
	::= { wirelessIfWORPStatsTableEntry 51 }

wirelessIfWORPStatsPollAutoReplies  OBJECT-TYPE
	SYNTAX     Counter32
	MAX-ACCESS read-only
	STATUS     current
	DESCRIPTION 
		"This parameter increments when SU auto replies after timeout."
	::= { wirelessIfWORPStatsTableEntry 52 }

wirelessIfWORPStatsDownlinkBE  OBJECT-TYPE
	SYNTAX     Unsigned32
	MAX-ACCESS read-only
	STATUS     current
	DESCRIPTION 
		"This parameter provides information about the Downlink Best Effort(BE) in Kbps."
	::= { wirelessIfWORPStatsTableEntry 53 }

-- =====================================================================================================
-- Definition of the Wireless Interface Blacklisted Channel info Group objects : wirelessIfBlacklistInfo
-- =====================================================================================================
-- Wireless Interface Blacklisted Info Table

wirelessIfBlacklistInfoTable  OBJECT-TYPE
	SYNTAX SEQUENCE OF WirelessIfBlacklistInfoTableEntry
	MAX-ACCESS not-accessible
	STATUS     deprecated
	DESCRIPTION 
		"This table shows the blacklisted channel information."
	::= { wirelessIfBlacklistInfo 1 }

wirelessIfBlacklistInfoTableEntry  OBJECT-TYPE
	SYNTAX 	WirelessIfBlacklistInfoTableEntry
	MAX-ACCESS not-accessible
	STATUS     deprecated
	DESCRIPTION 
		"This parameter represents an entry in the wireless interface
		             blacklisted info table."
	INDEX { wirelessIfBlacklistInfoTableIndex, 
		wirelessIfBlacklistInfoTableSecIndex }
	::= { wirelessIfBlacklistInfoTable 1 }

WirelessIfBlacklistInfoTableEntry ::= SEQUENCE {
	wirelessIfBlacklistInfoTableIndex
		Unsigned32,
	wirelessIfBlacklistInfoTableSecIndex
		Unsigned32,
	wirelessIfBlacklistedChannelNum
		Unsigned32,
	wirelessIfBlacklistReason
		DisplayString,
	wirelessIfBlacklistTimeElapsed
		Unsigned32
}

wirelessIfBlacklistInfoTableIndex  OBJECT-TYPE
	SYNTAX     Unsigned32 (1..2)
	MAX-ACCESS read-only
	STATUS     deprecated
	DESCRIPTION 
		"This parameter is used as index to the wirelessIfBlacklistInfoTable
		         and represents the radio number."
	::= { wirelessIfBlacklistInfoTableEntry 1 }

wirelessIfBlacklistInfoTableSecIndex  OBJECT-TYPE
	SYNTAX     Unsigned32
	MAX-ACCESS read-only
	STATUS     deprecated
	DESCRIPTION 
		"This parameter is used as secondary index to the wirelessIfBlacklistInfoTable
		         and represents the channel blacklisted."
	::= { wirelessIfBlacklistInfoTableEntry 2 }

wirelessIfBlacklistedChannelNum  OBJECT-TYPE
	SYNTAX     Unsigned32
	MAX-ACCESS read-only
	STATUS     deprecated
	DESCRIPTION 
		"This parameter shows the blacklisted channel number."
	::= { wirelessIfBlacklistInfoTableEntry 3 }

wirelessIfBlacklistReason  OBJECT-TYPE
	SYNTAX     DisplayString
	MAX-ACCESS read-only
	STATUS     deprecated
	DESCRIPTION 
		"This parameter shows the reason for the channel blacklisting."
	::= { wirelessIfBlacklistInfoTableEntry 4 }

wirelessIfBlacklistTimeElapsed  OBJECT-TYPE
	SYNTAX     Unsigned32
	MAX-ACCESS read-only
	STATUS     deprecated
	DESCRIPTION 
		"This parameter shows the time since the channel is blacklisted."
	::= { wirelessIfBlacklistInfoTableEntry 5 }

-- =========================================================================================
-- Definition of Wireless Interface WORP Link Test Subgroup Objects : wirelessIfWORPLinkTest
-- =========================================================================================
-- Wireless Interface WORP Link Test configuration Table

wirelessIfWORPLinkTestConfTable  OBJECT-TYPE
	SYNTAX SEQUENCE OF WirelessIfWORPLinkTestConfTableEntry
	MAX-ACCESS not-accessible
	STATUS     current
	DESCRIPTION 
		"This table holds the WORP link test configuration parameters."
	::= { wirelessIfWORPLinkTest 1 }

wirelessIfWORPLinkTestConfTableEntry  OBJECT-TYPE
	SYNTAX 	WirelessIfWORPLinkTestConfTableEntry
	MAX-ACCESS not-accessible
	STATUS     current
	DESCRIPTION 
		"This parameter represents the WORP link test conf table entry status."
	INDEX { wirelessIfWORPLinkTestConfTableIndex }
	::= { wirelessIfWORPLinkTestConfTable 1 }

WirelessIfWORPLinkTestConfTableEntry ::= SEQUENCE {
	wirelessIfWORPLinkTestConfTableIndex
		Unsigned32,
	wirelessIfWORPLinkTestExploreStatus
		INTEGER,
	wirelessIfWORPLinkTestProgressStatus
		INTEGER,
	wirelessIfWORPLinkTestIdleTimeout
		Unsigned32
}

wirelessIfWORPLinkTestConfTableIndex  OBJECT-TYPE
	SYNTAX     Unsigned32 (1)
	MAX-ACCESS read-only
	STATUS     current
	DESCRIPTION 
		"This parameter represents the index for the WORP link test conf table."
	::= { wirelessIfWORPLinkTestConfTableEntry 1 }

wirelessIfWORPLinkTestExploreStatus  OBJECT-TYPE
	SYNTAX     INTEGER {
		start (1),
		stop (2)
	}
	MAX-ACCESS read-write
	STATUS     current
	DESCRIPTION 
		"This parameter is used to start/stops WORP link test."
	::= { wirelessIfWORPLinkTestConfTableEntry 2 }

wirelessIfWORPLinkTestProgressStatus  OBJECT-TYPE
	SYNTAX     INTEGER {
		idle (1),
		inProgress (2),
		stopped (3),
		timeOut (4)
	}
	MAX-ACCESS read-only
	STATUS     current
	DESCRIPTION 
		"This parameter shows the progress of the WORP link test."
	::= { wirelessIfWORPLinkTestConfTableEntry 3 }

wirelessIfWORPLinkTestIdleTimeout  OBJECT-TYPE
	SYNTAX     Unsigned32
	MAX-ACCESS read-write
	STATUS     current
	DESCRIPTION 
		"The value of this parameter determines the time (in seconds) that a 
		link test will continue without any SNMP requests for a Link Test 
		Table entry.  When the time expires the Link Test Table is 
		cleared."
	DEFVAL  { 300 }
	::= { wirelessIfWORPLinkTestConfTableEntry 4 }

-- Wireless Interface WORP Link Test Stats Table

wirelessIfWORPLinkTestStatsTable  OBJECT-TYPE
	SYNTAX SEQUENCE OF WirelessIfWORPLinkTestStatsTableEntry
	MAX-ACCESS not-accessible
	STATUS     current
	DESCRIPTION 
		"This table contains the information for the stations currently 
		associated with the access point."
	::= { wirelessIfWORPLinkTest 5 }

wirelessIfWORPLinkTestStatsTableEntry  OBJECT-TYPE
	SYNTAX 	WirelessIfWORPLinkTestStatsTableEntry
	MAX-ACCESS not-accessible
	STATUS     current
	DESCRIPTION 
		"This parameter represents the entry in the Remote Link Test table."
	INDEX { wirelessIfWORPLinkTestStatsTableIndex, 
		wirelessIfWORPLinkTestStatsTableSecIndex }
	::= { wirelessIfWORPLinkTestStatsTable 1 }

WirelessIfWORPLinkTestStatsTableEntry ::= SEQUENCE {
	wirelessIfWORPLinkTestStatsTableIndex
		Unsigned32,
	wirelessIfWORPLinkTestStatsTableSecIndex
		Unsigned32,
	wirelessIfWORPLinkTestStatus
		INTEGER,
	wirelessIfWORPLinkTestStationName
		DisplayString,
	wirelessIfWORPLinkTestMACAddress
		MacAddress,
	wirelessIfWORPLinkTestWORPLinkStatus
		INTEGER,
	wirelessIfWORPLinkTestLocalCurSignal
		Integer32,
	wirelessIfWORPLinkTestLocalCurNoise
		Integer32,
	wirelessIfWORPLinkTestLocalCurSNR
		Integer32,
	wirelessIfWORPLinkTestLocalMinSignal
		Integer32,
	wirelessIfWORPLinkTestLocalMinNoise
		Integer32,
	wirelessIfWORPLinkTestLocalMinSNR
		Integer32,
	wirelessIfWORPLinkTestLocalMaxSignal
		Integer32,
	wirelessIfWORPLinkTestLocalMaxNoise
		Integer32,
	wirelessIfWORPLinkTestLocalMaxSNR
		Integer32,
	wirelessIfWORPLinkTestRemoteCurSignal
		Integer32,
	wirelessIfWORPLinkTestRemoteCurNoise
		Integer32,
	wirelessIfWORPLinkTestRemoteCurSNR
		Integer32,
	wirelessIfWORPLinkTestRemoteMinSignal
		Integer32,
	wirelessIfWORPLinkTestRemoteMinNoise
		Integer32,
	wirelessIfWORPLinkTestRemoteMinSNR
		Integer32,
	wirelessIfWORPLinkTestRemoteMaxSignal
		Integer32,
	wirelessIfWORPLinkTestRemoteMaxNoise
		Integer32,
	wirelessIfWORPLinkTestRemoteMaxSNR
		Integer32
}

wirelessIfWORPLinkTestStatsTableIndex  OBJECT-TYPE
	SYNTAX     Unsigned32
	MAX-ACCESS read-only
	STATUS     current
	DESCRIPTION 
		"This parameter represents a unique value for each station.  The 
		value for each station must remain constant at least from one 
		explore to the next."
	::= { wirelessIfWORPLinkTestStatsTableEntry 1 }

wirelessIfWORPLinkTestStatsTableSecIndex  OBJECT-TYPE
	SYNTAX     Unsigned32
	MAX-ACCESS read-only
	STATUS     current
	DESCRIPTION 
		"This parameter represents a unique value for each station.  The 
		value for each station must remain constant at least from one 
		explore to the next."
	::= { wirelessIfWORPLinkTestStatsTableEntry 2 }

wirelessIfWORPLinkTestStatus  OBJECT-TYPE
	SYNTAX     INTEGER {
		enable (1),
		disable (2)
	}
	MAX-ACCESS read-write
	STATUS     current
	DESCRIPTION 
		"When this parameter is set to 2 the device will initiate a link test 
		sequence with this station."
	::= { wirelessIfWORPLinkTestStatsTableEntry 3 }

wirelessIfWORPLinkTestStationName  OBJECT-TYPE
	SYNTAX     DisplayString
	MAX-ACCESS read-only
	STATUS     current
	DESCRIPTION 
		"This parameter identifies the name of the station whom which the 
		link test is being performed."
	::= { wirelessIfWORPLinkTestStatsTableEntry 4 }

wirelessIfWORPLinkTestMACAddress  OBJECT-TYPE
	SYNTAX     MacAddress
	MAX-ACCESS read-only
	STATUS     current
	DESCRIPTION 
		"This parameter represents the MAC address that will be mapped to 
		the IP Address of the station."
	::= { wirelessIfWORPLinkTestStatsTableEntry 5 }

wirelessIfWORPLinkTestWORPLinkStatus  OBJECT-TYPE
	SYNTAX     INTEGER {
		up (1),
		down (2)
	}
	MAX-ACCESS read-only
	STATUS     current
	DESCRIPTION 
		"This parameter shows the link status of WORP connectivity."
	::= { wirelessIfWORPLinkTestStatsTableEntry 6 }

wirelessIfWORPLinkTestLocalCurSignal  OBJECT-TYPE
	SYNTAX     Integer32
	MAX-ACCESS read-only
	STATUS     current
	DESCRIPTION 
		"The current signal level (in dB) for the link test from this 
		station.  This parameter indicates the running average of the local 
		signal level using the algorithm (3/4*oldvalue + 1/4*newvalue)."
	::= { wirelessIfWORPLinkTestStatsTableEntry 7 }

wirelessIfWORPLinkTestLocalCurNoise  OBJECT-TYPE
	SYNTAX     Integer32
	MAX-ACCESS read-only
	STATUS     current
	DESCRIPTION 
		"The current noise level (in dB) for the link test to this station. 
		This parameter indicates the running average of the local noise 
		level."
	::= { wirelessIfWORPLinkTestStatsTableEntry 8 }

wirelessIfWORPLinkTestLocalCurSNR  OBJECT-TYPE
	SYNTAX     Integer32
	MAX-ACCESS read-only
	STATUS     current
	DESCRIPTION 
		"The current signal to noise ratio for the link test to this 
		        station."
	::= { wirelessIfWORPLinkTestStatsTableEntry 9 }

wirelessIfWORPLinkTestLocalMinSignal  OBJECT-TYPE
	SYNTAX     Integer32
	MAX-ACCESS read-only
	STATUS     current
	DESCRIPTION 
		"The minimum signal level during the link test to this station."
	::= { wirelessIfWORPLinkTestStatsTableEntry 10 }

wirelessIfWORPLinkTestLocalMinNoise  OBJECT-TYPE
	SYNTAX     Integer32
	MAX-ACCESS read-only
	STATUS     current
	DESCRIPTION 
		"The minimum noise level during the link test to this station."
	::= { wirelessIfWORPLinkTestStatsTableEntry 11 }

wirelessIfWORPLinkTestLocalMinSNR  OBJECT-TYPE
	SYNTAX     Integer32
	MAX-ACCESS read-only
	STATUS     current
	DESCRIPTION 
		"The minimum signal to noise ratio during the link test to this 
		station."
	::= { wirelessIfWORPLinkTestStatsTableEntry 12 }

wirelessIfWORPLinkTestLocalMaxSignal  OBJECT-TYPE
	SYNTAX     Integer32
	MAX-ACCESS read-only
	STATUS     current
	DESCRIPTION 
		"The maximum signal level during the link test to this station."
	::= { wirelessIfWORPLinkTestStatsTableEntry 13 }

wirelessIfWORPLinkTestLocalMaxNoise  OBJECT-TYPE
	SYNTAX     Integer32
	MAX-ACCESS read-only
	STATUS     current
	DESCRIPTION 
		"The maximum noise level during the link test to this station."
	::= { wirelessIfWORPLinkTestStatsTableEntry 14 }

wirelessIfWORPLinkTestLocalMaxSNR  OBJECT-TYPE
	SYNTAX     Integer32
	MAX-ACCESS read-only
	STATUS     current
	DESCRIPTION 
		"The maximum signal to noise ratio during the link test to this 
		station."
	::= { wirelessIfWORPLinkTestStatsTableEntry 15 }

wirelessIfWORPLinkTestRemoteCurSignal  OBJECT-TYPE
	SYNTAX     Integer32
	MAX-ACCESS read-only
	STATUS     current
	DESCRIPTION 
		"The current signal level for the link test to the remote station 
		or access point."
	::= { wirelessIfWORPLinkTestStatsTableEntry 16 }

wirelessIfWORPLinkTestRemoteCurNoise  OBJECT-TYPE
	SYNTAX     Integer32
	MAX-ACCESS read-only
	STATUS     current
	DESCRIPTION 
		"The current noise level for the link test to the remote station
		or access point device."
	::= { wirelessIfWORPLinkTestStatsTableEntry 17 }

wirelessIfWORPLinkTestRemoteCurSNR  OBJECT-TYPE
	SYNTAX     Integer32
	MAX-ACCESS read-only
	STATUS     current
	DESCRIPTION 
		"The current signal to noise ratio for the link test to the remote 
		station or access point device."
	::= { wirelessIfWORPLinkTestStatsTableEntry 18 }

wirelessIfWORPLinkTestRemoteMinSignal  OBJECT-TYPE
	SYNTAX     Integer32
	MAX-ACCESS read-only
	STATUS     current
	DESCRIPTION 
		"The minimum signal level during the link test to the remote station
		or access point device."
	::= { wirelessIfWORPLinkTestStatsTableEntry 19 }

wirelessIfWORPLinkTestRemoteMinNoise  OBJECT-TYPE
	SYNTAX     Integer32
	MAX-ACCESS read-only
	STATUS     current
	DESCRIPTION 
		"The minimum noise level during the link test to the remote station 
		or access point device."
	::= { wirelessIfWORPLinkTestStatsTableEntry 20 }

wirelessIfWORPLinkTestRemoteMinSNR  OBJECT-TYPE
	SYNTAX     Integer32
	MAX-ACCESS read-only
	STATUS     current
	DESCRIPTION 
		"The minimum signal to noise ratio during the link test to the 
		remote station or access point device."
	::= { wirelessIfWORPLinkTestStatsTableEntry 21 }

wirelessIfWORPLinkTestRemoteMaxSignal  OBJECT-TYPE
	SYNTAX     Integer32
	MAX-ACCESS read-only
	STATUS     current
	DESCRIPTION 
		"The maximum signal level during the link test to the remote 
		station or access point device."
	::= { wirelessIfWORPLinkTestStatsTableEntry 22 }

wirelessIfWORPLinkTestRemoteMaxNoise  OBJECT-TYPE
	SYNTAX     Integer32
	MAX-ACCESS read-only
	STATUS     current
	DESCRIPTION 
		"The maximum noise level during the link test to the remote station 
		or access point device."
	::= { wirelessIfWORPLinkTestStatsTableEntry 23 }

wirelessIfWORPLinkTestRemoteMaxSNR  OBJECT-TYPE
	SYNTAX     Integer32
	MAX-ACCESS read-only
	STATUS     current
	DESCRIPTION 
		"The maximum signal to noise ratio during the link test to the 
		remote station or access point device."
	::= { wirelessIfWORPLinkTestStatsTableEntry 24 }

-- =========================================================================================
-- Definition of Wireless Interface Statistics Subgroup Objects : wirelessIfStats
-- =========================================================================================
-- Wireless Interface Statistics Table

wirelessIfStatsTable  OBJECT-TYPE
	SYNTAX SEQUENCE OF WirelessIfStatsTableEntry
	MAX-ACCESS not-accessible
	STATUS     current
	DESCRIPTION 
		"This table holds the statistics for the wireless interface(s)."
	::= { wirelessIfStats 1 }

wirelessIfStatsTableEntry  OBJECT-TYPE
	SYNTAX 	WirelessIfStatsTableEntry
	MAX-ACCESS not-accessible
	STATUS     current
	DESCRIPTION 
		"This parameter represents the entry for the wirelessIfStatsTable."
	INDEX { wirelessIfStatsTableIndex }
	::= { wirelessIfStatsTable 1 }

WirelessIfStatsTableEntry ::= SEQUENCE {
	wirelessIfStatsTableIndex
		Unsigned32,
	wirelessIfStatsTxPkts
		Counter32,
	wirelessIfStatsTxBytes
		Counter64,
	wirelessIfStatsRxPkts
		Counter32,
	wirelessIfStatsRxBytes
		Counter64,
	wirelessIfStatsRxDecryptErrors
		Counter64,
	wirelessIfStatsRxCRCErrors
		Counter64,
	wirelessIfStatsChain0CtlRSSI
		Integer32,
	wirelessIfStatsChain1CtlRSSI
		Integer32,
	wirelessIfStatsChain2CtlRSSI
		Integer32,
	wirelessIfStatsChain0ExtRSSI
		Integer32,
	wirelessIfStatsChain1ExtRSSI
		Integer32,
	wirelessIfStatsChain2ExtRSSI
		Integer32,
	wirelessIfStatsCombinedRSSI
		Integer32,
	wirelessIfStatsPhyErrors
		Integer32,
	wirelessIfStatsRadioReTunes
		Integer32,
	wirelessIfStatsCollisionFrames
		Integer32
}

wirelessIfStatsTableIndex  OBJECT-TYPE
	SYNTAX     Unsigned32
	MAX-ACCESS read-only
	STATUS     current
	DESCRIPTION 
		"This parameter represents the index for the wirelessIfStatsTable."
	::= { wirelessIfStatsTableEntry 1 }

wirelessIfStatsTxPkts  OBJECT-TYPE
	SYNTAX     Counter32
	MAX-ACCESS read-only
	STATUS     current
	DESCRIPTION 
		"This parameter shows the number of transmitted packets from the wireless
		                 interface."
	::= { wirelessIfStatsTableEntry 2 }

wirelessIfStatsTxBytes  OBJECT-TYPE
	SYNTAX     Counter64
	MAX-ACCESS read-only
	STATUS     current
	DESCRIPTION 
		"This parameter shows the number of transmitted bytes from the wireless
		                 interface."
	::= { wirelessIfStatsTableEntry 3 }

wirelessIfStatsRxPkts  OBJECT-TYPE
	SYNTAX     Counter32
	MAX-ACCESS read-only
	STATUS     current
	DESCRIPTION 
		"This parameter shows the number of received packets from the wireless
		                 interface."
	::= { wirelessIfStatsTableEntry 4 }

wirelessIfStatsRxBytes  OBJECT-TYPE
	SYNTAX     Counter64
	MAX-ACCESS read-only
	STATUS     current
	DESCRIPTION 
		"This parameter shows the number of received bytes from the wireless
		                 interface."
	::= { wirelessIfStatsTableEntry 5 }

wirelessIfStatsRxDecryptErrors  OBJECT-TYPE
	SYNTAX     Counter64
	MAX-ACCESS read-only
	STATUS     current
	DESCRIPTION 
		"This parameter shows the number of packets received with decryption errors on
		                 the wireless interface."
	::= { wirelessIfStatsTableEntry 6 }

wirelessIfStatsRxCRCErrors  OBJECT-TYPE
	SYNTAX     Counter64
	MAX-ACCESS read-only
	STATUS     current
	DESCRIPTION 
		"This parameter shows the number of packets received with CRC errors on the 
		                 wireless interface"
	::= { wirelessIfStatsTableEntry 7 }

wirelessIfStatsChain0CtlRSSI  OBJECT-TYPE
	SYNTAX     Integer32
	MAX-ACCESS read-only
	STATUS     current
	DESCRIPTION 
		"This parameter shows the control RSSI for the chain/antenna 0."
	::= { wirelessIfStatsTableEntry 8 }

wirelessIfStatsChain1CtlRSSI  OBJECT-TYPE
	SYNTAX     Integer32
	MAX-ACCESS read-only
	STATUS     current
	DESCRIPTION 
		"This parameter shows the control RSSI for the chain/antenna 1."
	::= { wirelessIfStatsTableEntry 9 }

wirelessIfStatsChain2CtlRSSI  OBJECT-TYPE
	SYNTAX     Integer32
	MAX-ACCESS read-only
	STATUS     current
	DESCRIPTION 
		"This parameter shows the control RSSI for the chain/antenna 2."
	::= { wirelessIfStatsTableEntry 10 }

wirelessIfStatsChain0ExtRSSI  OBJECT-TYPE
	SYNTAX     Integer32
	MAX-ACCESS read-only
	STATUS     current
	DESCRIPTION 
		"This parameter shows the Extension RSSI for the chain/antenna 0."
	::= { wirelessIfStatsTableEntry 11 }

wirelessIfStatsChain1ExtRSSI  OBJECT-TYPE
	SYNTAX     Integer32
	MAX-ACCESS read-only
	STATUS     current
	DESCRIPTION 
		"This parameter shows the Extension RSSI for the chain/antenna 1"
	::= { wirelessIfStatsTableEntry 12 }

wirelessIfStatsChain2ExtRSSI  OBJECT-TYPE
	SYNTAX     Integer32
	MAX-ACCESS read-only
	STATUS     current
	DESCRIPTION 
		"This parameter shows the Extension RSSI for the chain/antenna 2"
	::= { wirelessIfStatsTableEntry 13 }

wirelessIfStatsCombinedRSSI  OBJECT-TYPE
	SYNTAX     Integer32
	MAX-ACCESS read-only
	STATUS     current
	DESCRIPTION 
		"This parameter shows the combined RSSI of the control and extension."
	::= { wirelessIfStatsTableEntry 14 }

wirelessIfStatsPhyErrors  OBJECT-TYPE
	SYNTAX     Integer32
	MAX-ACCESS read-only
	STATUS     current
	DESCRIPTION 
		"This parameter shows the Physical layer errors."
	::= { wirelessIfStatsTableEntry 15 }

wirelessIfStatsRadioReTunes  OBJECT-TYPE
	SYNTAX     Integer32
	MAX-ACCESS read-only
	STATUS     current
	DESCRIPTION 
		"This parameter shows the Number of times the radio is re-tuned."
	::= { wirelessIfStatsTableEntry 16 }

wirelessIfStatsCollisionFrames  OBJECT-TYPE
	SYNTAX     Integer32
	MAX-ACCESS read-only
	STATUS     current
	DESCRIPTION 
		"This Parameter shows the No. of Collisions."
	::= { wirelessIfStatsTableEntry 17 }

-- -----------------------------------------------------------------------------
-- Wireless Interface SNR Table

wirelessIfSnrInfoTable  OBJECT-TYPE
	SYNTAX SEQUENCE OF WirelessIfSnrInfoTableEntry
	MAX-ACCESS not-accessible
	STATUS     current
	DESCRIPTION 
		"This table contains the information of minimum and maxmimum snr
		 snr associated with the wireless interface."
	::= { wirelessIfSnrInfo 1 }

wirelessIfSnrInfoTableEntry  OBJECT-TYPE
	SYNTAX 	WirelessIfSnrInfoTableEntry
	MAX-ACCESS not-accessible
	STATUS     current
	DESCRIPTION 
		"This parameter represents the entry in the SNR table."
	INDEX { wirelessIfSnrInfoTableIndex, 
		wirelessIfSnrInfoTableSecIndex }
	::= { wirelessIfSnrInfoTable 1 }

WirelessIfSnrInfoTableEntry ::= SEQUENCE {
	wirelessIfSnrInfoTableIndex
		Unsigned32,
	wirelessIfSnrInfoTableSecIndex
		Unsigned32,
	wirelessIfSnrInfoMCSIndex
		DisplayString,
	wirelessIfSnrInfoPhyModulation
		DisplayString,
	wirelessIfSnrInfoStreamMode
		DisplayString,
	wirelessIfSnrInfoDataRate
		DisplayString,
	wirelessIfSnrInfoMinReqSNR
		Unsigned32,
	wirelessIfSnrInfoMaxReqSNR
		Unsigned32
}

wirelessIfSnrInfoTableIndex  OBJECT-TYPE
	SYNTAX     Unsigned32
	MAX-ACCESS read-only
	STATUS     current
	DESCRIPTION 
		""
	::= { wirelessIfSnrInfoTableEntry 1 }

wirelessIfSnrInfoTableSecIndex  OBJECT-TYPE
	SYNTAX     Unsigned32
	MAX-ACCESS read-only
	STATUS     current
	DESCRIPTION 
		""
	::= { wirelessIfSnrInfoTableEntry 2 }

wirelessIfSnrInfoMCSIndex  OBJECT-TYPE
	SYNTAX     DisplayString
	MAX-ACCESS read-only
	STATUS     current
	DESCRIPTION 
		""
	::= { wirelessIfSnrInfoTableEntry 3 }

wirelessIfSnrInfoPhyModulation  OBJECT-TYPE
	SYNTAX     DisplayString
	MAX-ACCESS read-only
	STATUS     current
	DESCRIPTION 
		""
	::= { wirelessIfSnrInfoTableEntry 4 }

wirelessIfSnrInfoStreamMode  OBJECT-TYPE
	SYNTAX     DisplayString
	MAX-ACCESS read-only
	STATUS     current
	DESCRIPTION 
		""
	::= { wirelessIfSnrInfoTableEntry 5 }

wirelessIfSnrInfoDataRate  OBJECT-TYPE
	SYNTAX     DisplayString
	MAX-ACCESS read-only
	STATUS     current
	DESCRIPTION 
		""
	::= { wirelessIfSnrInfoTableEntry 6 }

wirelessIfSnrInfoMinReqSNR  OBJECT-TYPE
	SYNTAX     Unsigned32 (1..100)
	MAX-ACCESS read-only
	STATUS     current
	DESCRIPTION 
		""
	::= { wirelessIfSnrInfoTableEntry 7 }

wirelessIfSnrInfoMaxReqSNR  OBJECT-TYPE
	SYNTAX     Unsigned32 (1..100)
	MAX-ACCESS read-only
	STATUS     current
	DESCRIPTION 
		""
	::= { wirelessIfSnrInfoTableEntry 8 }

-- wirelessIfDFSInfo Table

wirelessIfDFSInfoTable  OBJECT-TYPE
	SYNTAX SEQUENCE OF WirelessIfDFSInfoEntry
	MAX-ACCESS not-accessible
	STATUS     current
	DESCRIPTION 
		""
	::= { wirelessIfDFSInfo 1 }

wirelessIfDFSInfoEntry  OBJECT-TYPE
	SYNTAX 	WirelessIfDFSInfoEntry
	MAX-ACCESS not-accessible
	STATUS     current
	DESCRIPTION 
		""
	INDEX { wirelessIfDFSInfoTableIndex, 
		wirelessIfDFSInfoTableSecIndex }
	::= { wirelessIfDFSInfoTable 1 }

WirelessIfDFSInfoEntry ::= SEQUENCE {
	wirelessIfDFSInfoTableIndex
		Unsigned32,
	wirelessIfDFSInfoTableSecIndex
		Unsigned32,
	wirelessIfDFSInfoStartFrequency
		Unsigned32,
	wirelessIfDFSInfoEndFrequency
		Unsigned32,
	wirelessIfDFSInfoBlacklistReason
		DisplayString,
	wirelessIfDFSInfoTimeElapsed
		Unsigned32
}

wirelessIfDFSInfoTableIndex  OBJECT-TYPE
	SYNTAX     Unsigned32
	MAX-ACCESS read-only
	STATUS     current
	DESCRIPTION 
		""
	::= { wirelessIfDFSInfoEntry 1 }

wirelessIfDFSInfoTableSecIndex  OBJECT-TYPE
	SYNTAX     Unsigned32
	MAX-ACCESS read-only
	STATUS     current
	DESCRIPTION 
		""
	::= { wirelessIfDFSInfoEntry 2 }

wirelessIfDFSInfoStartFrequency  OBJECT-TYPE
	SYNTAX     Unsigned32 (0..10000)
	MAX-ACCESS read-only
	STATUS     current
	DESCRIPTION 
		""
	::= { wirelessIfDFSInfoEntry 3 }

wirelessIfDFSInfoEndFrequency  OBJECT-TYPE
	SYNTAX     Unsigned32 (0..10000)
	MAX-ACCESS read-only
	STATUS     current
	DESCRIPTION 
		""
	::= { wirelessIfDFSInfoEntry 4 }

wirelessIfDFSInfoBlacklistReason  OBJECT-TYPE
	SYNTAX     DisplayString
	MAX-ACCESS read-only
	STATUS     current
	DESCRIPTION 
		""
	::= { wirelessIfDFSInfoEntry 5 }

wirelessIfDFSInfoTimeElapsed  OBJECT-TYPE
	SYNTAX     Unsigned32
	MAX-ACCESS read-only
	STATUS     current
	DESCRIPTION 
		""
	::= { wirelessIfDFSInfoEntry 6 }

-- =============================================================================
-- Definition of Radius Client Statistics Subgroup Objects : radiusClientStats
-- =============================================================================
-- Radius Client Authentication Stats Table

radiusClientAuthStatsTable  OBJECT-TYPE
	SYNTAX SEQUENCE OF RadiusClientAuthStatsTableEntry
	MAX-ACCESS not-accessible
	STATUS     current
	DESCRIPTION 
		"This table is used to store RADIUS Authentication Client
		 Statistics for the configured profiles."
	::= { radiusClientStats 1 }

radiusClientAuthStatsTableEntry  OBJECT-TYPE
	SYNTAX 	RadiusClientAuthStatsTableEntry
	MAX-ACCESS not-accessible
	STATUS     current
	DESCRIPTION 
		"This parameter represents an entry in the radiusClientAuthStatsTable.
		 Note this table is indexed by VAP and Radius Pri/Sec servers"
	INDEX { radiusClientAuthStatsTableIndex, 
		radiusClientAuthStatsTableSecIndex }
	::= { radiusClientAuthStatsTable 1 }

RadiusClientAuthStatsTableEntry ::= SEQUENCE {
	radiusClientAuthStatsTableIndex
		Unsigned32,
	radiusClientAuthStatsTableSecIndex
		Unsigned32,
	radiusClientAuthStatsRoundTripTime
		TimeTicks,
	radiusClientAuthStatsRequests
		Counter32,
	radiusClientAuthStatsRetransmissions
		Counter32,
	radiusClientAuthStatsAccessAccepts
		Counter32,
	radiusClientAuthStatsAccessRejects
		Counter32,
	radiusClientAuthStatsAccessChallenges
		Counter32,
	radiusClientAuthStatsResponses
		Counter32,
	radiusClientAuthStatsMalformedResponses
		Counter32,
	radiusClientAuthStatsBadAuthenticators
		Counter32,
	radiusClientAuthStatsTimeouts
		Counter32,
	radiusClientAuthStatsUnknownTypes
		Counter32,
	radiusClientAuthStatsPacketsDropped
		Counter32
}

radiusClientAuthStatsTableIndex  OBJECT-TYPE
	SYNTAX     Unsigned32 (1..16)
	MAX-ACCESS read-only
	STATUS     current
	DESCRIPTION 
		"This parameter is user defined parameter and used as an 
		 index for Radius client Authorization status."
	::= { radiusClientAuthStatsTableEntry 1 }

radiusClientAuthStatsTableSecIndex  OBJECT-TYPE
	SYNTAX     Unsigned32 (1..2)
	MAX-ACCESS read-only
	STATUS     current
	DESCRIPTION 
		"This parameter is secondary index to Radius client 
		 Authorisation status, 1 represents the primary server and 
		 2 represents the secondary server."
	::= { radiusClientAuthStatsTableEntry 2 }

radiusClientAuthStatsRoundTripTime  OBJECT-TYPE
	SYNTAX     TimeTicks
	MAX-ACCESS read-only
	STATUS     current
	DESCRIPTION 
		"This parameter represents the round trip time for messages
		 exchanged between radius client and authentication server 
		 since system startup."
	::= { radiusClientAuthStatsTableEntry 3 }

radiusClientAuthStatsRequests  OBJECT-TYPE
	SYNTAX     Counter32
	MAX-ACCESS read-only
	STATUS     current
	DESCRIPTION 
		"This parameter represents the number of RADIUS Access 
		 Requests messages transmitted from the client to the 
		 server since client startup."
	::= { radiusClientAuthStatsTableEntry 4 }

radiusClientAuthStatsRetransmissions  OBJECT-TYPE
	SYNTAX     Counter32
	MAX-ACCESS read-only
	STATUS     current
	DESCRIPTION 
		"This parameter represents the number of RADIUS Access 
		 Requests retransmitted by the client to the server since 
		 system startup."
	::= { radiusClientAuthStatsTableEntry 5 }

radiusClientAuthStatsAccessAccepts  OBJECT-TYPE
	SYNTAX     Counter32
	MAX-ACCESS read-only
	STATUS     current
	DESCRIPTION 
		"This parameter indicates the number of RADIUS Access 
		 Accept messages received since system startup."
	::= { radiusClientAuthStatsTableEntry 6 }

radiusClientAuthStatsAccessRejects  OBJECT-TYPE
	SYNTAX     Counter32
	MAX-ACCESS read-only
	STATUS     current
	DESCRIPTION 
		"This parameter represents the number of RADIUS Access 
		 Rejects  messages received since system startup."
	::= { radiusClientAuthStatsTableEntry 7 }

radiusClientAuthStatsAccessChallenges  OBJECT-TYPE
	SYNTAX     Counter32
	MAX-ACCESS read-only
	STATUS     current
	DESCRIPTION 
		"This parameter represents the number of RADIUS Access 
		 Challenges messages received since system startup."
	::= { radiusClientAuthStatsTableEntry 8 }

radiusClientAuthStatsResponses  OBJECT-TYPE
	SYNTAX     Counter32
	MAX-ACCESS read-only
	STATUS     current
	DESCRIPTION 
		"This parameter represents the total number of RADIUS 
		 Access messages received from the authentication server 
		 since system startup."
	::= { radiusClientAuthStatsTableEntry 9 }

radiusClientAuthStatsMalformedResponses  OBJECT-TYPE
	SYNTAX     Counter32
	MAX-ACCESS read-only
	STATUS     current
	DESCRIPTION 
		"This parameter represents the number of malformed RADIUS 
		 Access Response messages received since system startup."
	::= { radiusClientAuthStatsTableEntry 10 }

radiusClientAuthStatsBadAuthenticators  OBJECT-TYPE
	SYNTAX     Counter32
	MAX-ACCESS read-only
	STATUS     current
	DESCRIPTION 
		"This parameter represents the number of malformed RADIUS
		 Access Response messages containing invalid authenticators 
		                 received since system startup."
	::= { radiusClientAuthStatsTableEntry 11 }

radiusClientAuthStatsTimeouts  OBJECT-TYPE
	SYNTAX     Counter32
	MAX-ACCESS read-only
	STATUS     current
	DESCRIPTION 
		"This parameters represents the total number of timeouts 
		 for RADIUS Access Request messages since system startup."
	::= { radiusClientAuthStatsTableEntry 12 }

radiusClientAuthStatsUnknownTypes  OBJECT-TYPE
	SYNTAX     Counter32
	MAX-ACCESS read-only
	STATUS     current
	DESCRIPTION 
		"This parameter represents the number of messages with unknown
		 Radius Message Code since system startup."
	::= { radiusClientAuthStatsTableEntry 13 }

radiusClientAuthStatsPacketsDropped  OBJECT-TYPE
	SYNTAX     Counter32
	MAX-ACCESS read-only
	STATUS     current
	DESCRIPTION 
		"This parameter represents the number of Radius messages which do 
		 not contain any EAP payloads  or EAP State machine do not have 
		 any valid EAP state data since system startup."
	::= { radiusClientAuthStatsTableEntry 14 }

-- Radius Client Accounting Stats Table

radiusClientAccStatsTable  OBJECT-TYPE
	SYNTAX SEQUENCE OF RadiusClientAccStatsTableEntry
	MAX-ACCESS not-accessible
	STATUS     current
	DESCRIPTION 
		"This table is used to store RADIUS Accounting Client Statistics 
		 for the configured profiles."
	::= { radiusClientStats 2 }

radiusClientAccStatsTableEntry  OBJECT-TYPE
	SYNTAX 	RadiusClientAccStatsTableEntry
	MAX-ACCESS not-accessible
	STATUS     current
	DESCRIPTION 
		"This parameter represents an entry in the radiusClientAccStatsTable.
		 Note this table is indexed by VAP and Radius Pri/Sec servers."
	INDEX { radiusClientAccStatsTableIndex, 
		radiusClientAccStatsTableSecIndex }
	::= { radiusClientAccStatsTable 1 }

RadiusClientAccStatsTableEntry ::= SEQUENCE {
	radiusClientAccStatsTableIndex
		Unsigned32,
	radiusClientAccStatsTableSecIndex
		Unsigned32,
	radiusClientAccStatsRoundTripTime
		TimeTicks,
	radiusClientAccStatsRequests
		Counter32,
	radiusClientAccStatsRetransmissions
		Counter32,
	radiusClientAccStatsResponses
		Counter32,
	radiusClientAccStatsMalformedResponses
		Counter32,
	radiusClientAccStatsTimeouts
		Counter32,
	radiusClientAccStatsUnknownTypes
		Counter32,
	radiusClientAccStatsPacketsDropped
		Counter32
}

radiusClientAccStatsTableIndex  OBJECT-TYPE
	SYNTAX     Unsigned32 (1..16)
	MAX-ACCESS read-only
	STATUS     current
	DESCRIPTION 
		"This parameter is used as an index to the RADIUS Accounting
		 Client Statistics Table."
	::= { radiusClientAccStatsTableEntry 1 }

radiusClientAccStatsTableSecIndex  OBJECT-TYPE
	SYNTAX     Unsigned32 (1..2)
	MAX-ACCESS read-only
	STATUS     current
	DESCRIPTION 
		"This parameter is used as secondary index to the RADIUS 
		 Accounting Client Statistics Table, which is used to indicate 
		 primary and secondary/backup server statistics, 1 represents 
		 the Primary server and 2 represents the Secondary server.
		"
	::= { radiusClientAccStatsTableEntry 2 }

radiusClientAccStatsRoundTripTime  OBJECT-TYPE
	SYNTAX     TimeTicks
	MAX-ACCESS read-only
	STATUS     current
	DESCRIPTION 
		"This parameter represents the round trip time for messages 
		 exchanged between radius client and authentication server 
		 since system startup ."
	::= { radiusClientAccStatsTableEntry 3 }

radiusClientAccStatsRequests  OBJECT-TYPE
	SYNTAX     Counter32
	MAX-ACCESS read-only
	STATUS     current
	DESCRIPTION 
		"This parameter represents the number of RADIUS Accounting 
		 Requests messages transmitted from the client to the server 
		 since client startup. "
	::= { radiusClientAccStatsTableEntry 4 }

radiusClientAccStatsRetransmissions  OBJECT-TYPE
	SYNTAX     Counter32
	MAX-ACCESS read-only
	STATUS     current
	DESCRIPTION 
		"This parameter represents the number of RADIUS Accounting 
		 Requests retransmitted by the client to the server since 
		 system startup. "
	::= { radiusClientAccStatsTableEntry 5 }

radiusClientAccStatsResponses  OBJECT-TYPE
	SYNTAX     Counter32
	MAX-ACCESS read-only
	STATUS     current
	DESCRIPTION 
		"This parameter indicates the number of RADIUS Accounting 
		 Response messages received since system startup. "
	::= { radiusClientAccStatsTableEntry 6 }

radiusClientAccStatsMalformedResponses  OBJECT-TYPE
	SYNTAX     Counter32
	MAX-ACCESS read-only
	STATUS     current
	DESCRIPTION 
		"This parameter represents the number of malformed RADIUS 
		 Access Response messages received since system startup."
	::= { radiusClientAccStatsTableEntry 7 }

radiusClientAccStatsTimeouts  OBJECT-TYPE
	SYNTAX     Counter32
	MAX-ACCESS read-only
	STATUS     current
	DESCRIPTION 
		"This parameter represents the total number of timeouts for 
		 RADIUS Accounting Response messages since the system startup."
	::= { radiusClientAccStatsTableEntry 8 }

radiusClientAccStatsUnknownTypes  OBJECT-TYPE
	SYNTAX     Counter32
	MAX-ACCESS read-only
	STATUS     current
	DESCRIPTION 
		"This parameter represents the number of messages with unknown
		 Radius Message Code since system startup. "
	::= { radiusClientAccStatsTableEntry 9 }

radiusClientAccStatsPacketsDropped  OBJECT-TYPE
	SYNTAX     Counter32
	MAX-ACCESS read-only
	STATUS     current
	DESCRIPTION 
		"This parameter represents the number of Radius messages which 
		 do not contain any EAP payloads or EAP State machine do not 
		 have any valid EAP state data since system startup. "
	::= { radiusClientAccStatsTableEntry 10 }

-- =============================================================================
-- Definition of traps Group Objects 
-- =============================================================================
-- =============================================================================
-- Definition of Interface Traps Subgroup Objects : interfaceTraps
-- =============================================================================
-- Wireless Interface Card Initialization Failure

wirelessInterfaceCardInitFailure  NOTIFICATION-TYPE
	OBJECTS { genericTrap }
	STATUS     current
	DESCRIPTION 
		"This trap is generated when a wireless interface card is not  
		 present in the device or not initialized properly. 
		         Trap Severity Level: Critical."
	::= { interfaceTraps 1 }

-- Wireless Interface Card Radar Interference Detection

wirelessInterfaceCardRadarInterferenceDetected  NOTIFICATION-TYPE
	OBJECTS { genericTrap }
	STATUS     current
	DESCRIPTION 
		"This trap is generated when radar interference is detected on the             
		                 channel being used by the wireless interface.  The generic trap 
		                 varible provides information on the channel where interference 
		                 was detected. 
		         Trap Severity Level: Major."
	::= { interfaceTraps 2 }

-- Wireless Interface Invalid Reg Domain

wirelessInterfaceInvalidRegDomain  NOTIFICATION-TYPE
	OBJECTS { genericTrap }
	STATUS     current
	DESCRIPTION 
		"This trap is generated when the Regulatory Domain is invalid. 
		Trap Severity Level: Major."
	::= { interfaceTraps 3 }

-- Wireless Interface World Mode Not Set

wirelessInterfaceWorldModeCCNotSet  NOTIFICATION-TYPE
	OBJECTS { genericTrap }
	STATUS     current
	DESCRIPTION 
		"This trap is generated when the WorldModeCountryCode is not set. 
		Trap Severity Level: Major."
	::= { interfaceTraps 4 }

-- Wireless Interface Channel changed

wirelessInterfaceChannelChanged  NOTIFICATION-TYPE
	OBJECTS { genericTrap }
	STATUS     current
	DESCRIPTION 
		"This trap is generated Wireless Interface Channel is changed. 
		                Trap Severity Level: Informational."
	::= { interfaceTraps 5 }

-- Wireless WORP Station DissAssociation

wirelessInterfaceStationDissAssociation  NOTIFICATION-TYPE
	OBJECTS { genericTrap }
	STATUS     deprecated
	DESCRIPTION 
		"This trap is generated when a station is dissassociated from BSU. 
		                Trap Severity Level: Informational.
		                This is now deprecated. Instead use worpStationDeregister"
	::= { interfaceTraps 6 }

-- =============================================================================
-- Definition of security Traps Subgroup Objects : securityTraps
-- ============================================================================= 
-- Radius Server Not Responding

radiusSrvNotResponding  NOTIFICATION-TYPE
	OBJECTS { genericTrap }
	STATUS     current
	DESCRIPTION 
		"This trap is generated when no response is received from the 
		                 RADIUS server(s) for authentication requests sent from the RADIUS 
		                 client in the device. 
		 Trap Severity Level: Major."
	::= { securityTraps 1 }

authenticationFailure  NOTIFICATION-TYPE
	OBJECTS { genericTrap }
	STATUS     current
	DESCRIPTION 
		"This trap is generated when a client authentication failure  
		has occurred.  The authentication failures can range from: 
		    - MAC Access Control Table 
		    - RADIUS MAC Authentication 
		    - 802.1x Authentication specifying the EAP-Type 
		    - WORP Mutual Authentication 
		    - SSID Authorization Failure specifying the SSID 
		    - VLAN ID Authorization Failure specifying the VLAN ID 
		Trap Severity Level: Major."
	::= { securityTraps 2 }

-- =============================================================================
-- Definition of Operational Traps Subgroup Objects : operationalTraps
-- ============================================================================= 
-- Master Agent Exited

masterAgentExited  NOTIFICATION-TYPE
	OBJECTS { genericTrap }
	STATUS     current
	DESCRIPTION 
		"This trap is generated when the SNMP master agent is exited or killed. 
		 Trap Severity Level: Critical."
	::= { operationalTraps 1 }

-- Image Download Failed

imageDownloadFailed  NOTIFICATION-TYPE
	OBJECTS { genericTrap }
	STATUS     current
	DESCRIPTION 
		"This trap is generated when the image download is failed. 
		 Trap Severity Level: Critical."
	::= { operationalTraps 2 }

-- Signature Check Failed

signatureCheckFailed  NOTIFICATION-TYPE
	OBJECTS { genericTrap }
	STATUS     current
	DESCRIPTION 
		"This trap is generated when the signature check is failed while
		 downloading the image. 
		 Trap Severity Level: Critical."
	::= { operationalTraps 3 }

-- All Configurations Applied Successfully 

configurationAppliedSuccessfully  NOTIFICATION-TYPE
	OBJECTS { genericTrap }
	STATUS     current
	DESCRIPTION 
		"This trap is generated when commit is passed, i.e., the changed 
		 configurations are applied successfully.
		Trap Severity Level: Major."
	::= { operationalTraps 4 }

moduleNotInitialized  NOTIFICATION-TYPE
	OBJECTS { genericTrap }
	STATUS     current
	DESCRIPTION 
		"This trap is generated when a certain software or hardware module  
		has not been initialized or failed to be initialized. 
		Trap Severity Level: Major."
	::= { operationalTraps 5 }

deviceRebooting  NOTIFICATION-TYPE
	OBJECTS { genericTrap }
	STATUS     current
	DESCRIPTION 
		"This trap is generated when the device has received a request  
		to be rebooted. 
		Trap Severity Level: Informational."
	::= { operationalTraps 6 }

suEthernetStatusUp  NOTIFICATION-TYPE
	OBJECTS { genericTrap }
	STATUS     current
	DESCRIPTION 
		"This trap is generated by the SU when the ETHERNET Interface comes UP 
		    Trap Severity Level : Informational"
	::= { operationalTraps 7 }

suEthernetStatusDown  NOTIFICATION-TYPE
	OBJECTS { genericTrap }
	STATUS     current
	DESCRIPTION 
		"This trap is generated by the SU when the ETHERNET Interface comes DOWN 
		    Trap Severity Level : Informational"
	::= { operationalTraps 8 }

-- =============================================================================
-- Definition of System Traps Subgroup Objects : systemTraps
-- ============================================================================= 
-- Invalid Configuration File

invalidConfigFile  NOTIFICATION-TYPE
	OBJECTS { genericTrap }
	STATUS     current
	DESCRIPTION 
		"This trap is generated when an invalid image is loaded on the 
		                      device. 
		        Trap Severity Level: Major."
	::= { systemTraps 1 }

-- CPU Usage Threshold Exceeded

cpuUsageThresholdExceeded  NOTIFICATION-TYPE
	OBJECTS { genericTrap }
	STATUS     current
	DESCRIPTION 
		"This trap is generated when the CPU usage threshold is exceeded. 
		Trap Severity Level: Critical."
	::= { systemTraps 2 }

-- Flash Memory Threshold Exceeded

flashMemoryThresholdExceeded  NOTIFICATION-TYPE
	OBJECTS { genericTrap }
	STATUS     current
	DESCRIPTION 
		"This trap is generated when the flash memory is full or beyond 
		 the limit. 
		Trap Severity Level: Critical."
	::= { systemTraps 3 }

-- RAM Memory Threshold Exceeded

ramMemoryThresholdExceeded  NOTIFICATION-TYPE
	OBJECTS { genericTrap }
	STATUS     current
	DESCRIPTION 
		"This trap is generated when the ram memory is full or beyond 
		 the limit. 
		Trap Severity Level: Critical."
	::= { systemTraps 4 }

-- Invalid License File

invalidLicenseFile  NOTIFICATION-TYPE
	OBJECTS { genericTrap }
	STATUS     current
	DESCRIPTION 
		"This trap is generated when the invalid license file is loaded. 
		        Trap Severity Level: Critical."
	::= { systemTraps 5 }

-- PXM Modules Initialized successfully

pxmModulesInitSuccess  NOTIFICATION-TYPE
	OBJECTS { genericTrap }
	STATUS     current
	DESCRIPTION 
		"This trap is generated when the initialization of all PXM MODULES
		 is success.  
		Trap Severity Level: Major."
	::= { systemTraps 6 }

-- SysMgmt Modules Initialization Failure

sysMgmtModulesInitFailure  NOTIFICATION-TYPE
	OBJECTS { genericTrap }
	STATUS     current
	DESCRIPTION 
		"This trap is generated when the initialization of SYSMGMT module
		 is failed.  
		Trap Severity Level: Major."
	::= { systemTraps 7 }

-- VLAN Module Initialization Failure

vlanModuleInitFailure  NOTIFICATION-TYPE
	OBJECTS { genericTrap }
	STATUS     current
	DESCRIPTION 
		"This trap is generated when the initialization of VLAN module
		 is failed. 
		Trap Severity Level: Major."
	::= { systemTraps 8 }

-- Filtering Module Initialization Failure

filteringModuleInitFailure  NOTIFICATION-TYPE
	OBJECTS { genericTrap }
	STATUS     current
	DESCRIPTION 
		"This trap is generated when the initialization of FILTERING module
		 is failed. 
		Trap Severity Level: Major."
	::= { systemTraps 9 }

-- SysUtils Module Initialization Failure

sysutilsModuleInitFailure  NOTIFICATION-TYPE
	OBJECTS { genericTrap }
	STATUS     current
	DESCRIPTION 
		"This trap is generated when the initialization of SYSUTILS module
		 is failed. 
		Trap Severity Level: Major."
	::= { systemTraps 10 }

-- TFTP Module Initialization Failure

tftpModuleInitFailure  NOTIFICATION-TYPE
	OBJECTS { genericTrap }
	STATUS     current
	DESCRIPTION 
		"This trap is generated when the initialization of TFTP module
		 is failed. 
		Trap Severity Level: Major."
	::= { systemTraps 11 }

-- SNTP Module Initialization Failure

sntpModuleInitFailure  NOTIFICATION-TYPE
	OBJECTS { genericTrap }
	STATUS     current
	DESCRIPTION 
		"This trap is generated when the initialization of SNTP module
		 is failed. 
		Trap Severity Level: Major."
	::= { systemTraps 12 }

-- Syslog Module Initialization Failure

syslogModuleInitFailure  NOTIFICATION-TYPE
	OBJECTS { genericTrap }
	STATUS     current
	DESCRIPTION 
		"This trap is generated when the initialization of SYSLOG module
		 is failed. 
		Trap Severity Level: Major."
	::= { systemTraps 13 }

-- WLAN Module Initialization Failure

wlanModuleInitFailure  NOTIFICATION-TYPE
	OBJECTS { genericTrap }
	STATUS     current
	DESCRIPTION 
		"This trap is generated when the initialization of WLAN module
		 is failed. 
		Trap Severity Level: Major."
	::= { systemTraps 14 }

-- Flash Module Initialization Failure

flashModuleInitFailure  NOTIFICATION-TYPE
	OBJECTS { genericTrap }
	STATUS     current
	DESCRIPTION 
		"This trap is generated when the initialization of FLASH module
		 is failed. 
		Trap Severity Level: Major."
	::= { systemTraps 15 }

-- SNMP Module Initialization Failure

snmpModuleInitFailure  NOTIFICATION-TYPE
	OBJECTS { genericTrap }
	STATUS     current
	DESCRIPTION 
		"This trap is generated when the initialization of SNMP module
		 is failed.
		Trap Severity Level: Major."
	::= { systemTraps 16 }

-- System Temperature reached the max/min limits

systemTempReachedLimits  NOTIFICATION-TYPE
	OBJECTS { genericTrap }
	STATUS     current
	DESCRIPTION 
		"This trap is generated when the system temperature reaches the maximum/
		                 minimum limits or the proximity of the max/min limits.
		Trap Severity Level: Major."
	::= { systemTraps 17 }

-- DHCP Relay Module Initialization Failure

dhcpRelayModuleInitFailure  NOTIFICATION-TYPE
	OBJECTS { genericTrap }
	STATUS     current
	DESCRIPTION 
		"This trap is generated when the initialization of DHCP Relay module
		                 is failed.
		                Trap Severity Level: Major."
	::= { systemTraps 18 }

-- DHCP Server Module Initialization Failure

dhcpServerModuleInitFailure  NOTIFICATION-TYPE
	OBJECTS { genericTrap }
	STATUS     current
	DESCRIPTION 
		"This trap is generated when the initialization of DHCP Server module
		                 is failed.
		                Trap Severity Level: Major."
	::= { systemTraps 19 }

-- Static NAT Module Initialization Failure

staticNATModuleInitFailure  NOTIFICATION-TYPE
	OBJECTS { genericTrap }
	STATUS     current
	DESCRIPTION 
		"This trap is generated when the initialization of Static NAT module
		                 is failed.
		                Trap Severity Level: Major."
	::= { systemTraps 20 }

-- License Module Initialization Failure

licenseModuleInitFailure  NOTIFICATION-TYPE
	OBJECTS { genericTrap }
	STATUS     current
	DESCRIPTION 
		"This trap is generated when the initialization of License module
		                 is failed.
		                Trap Severity Level: Major."
	::= { systemTraps 21 }

-- System Features Module Initialization Failure

systemFeatureModuleInitFailure  NOTIFICATION-TYPE
	OBJECTS { genericTrap }
	STATUS     current
	DESCRIPTION 
		"This trap is generated when the initialization of System Features module
		                 is failed.
		                Trap Severity Level: Major."
	::= { systemTraps 22 }

-- Management Access Module Initialization Failure

mgmtAccessModuleInitFailure  NOTIFICATION-TYPE
	OBJECTS { genericTrap }
	STATUS     current
	DESCRIPTION 
		"This trap is generated when the initialization of Management Access module
		                 is failed.
		                Trap Severity Level: Major."
	::= { systemTraps 23 }

-- Routing Module Initialization Failure

routingModuleInitFailure  NOTIFICATION-TYPE
	OBJECTS { genericTrap }
	STATUS     current
	DESCRIPTION 
		"This trap is generated when the initialization of Routing module
		                 is failed.
		                Trap Severity Level: Major."
	::= { systemTraps 24 }

pppoeModuleSessionConnected  NOTIFICATION-TYPE
	OBJECTS { genericTrap }
	STATUS     current
	DESCRIPTION 
		"This trap is generated when the pppoe session is connected
		Trap Severity Level: Major."
	::= { systemTraps 25 }

pppoeModuleSessionDisconnected  NOTIFICATION-TYPE
	OBJECTS { genericTrap }
	STATUS     current
	DESCRIPTION 
		"This trap is generated when the pppoe session is disconnected
		                Trap Severity Level: Major."
	::= { systemTraps 26 }

pppoeModuleInitFailure  NOTIFICATION-TYPE
	OBJECTS { genericTrap }
	STATUS     current
	DESCRIPTION 
		"This trap is generated when the initialization of PPPoE module
		                 is failed.
		                Trap Severity Level: Major."
	::= { systemTraps 27 }

autoConfigRecoveryTrap  NOTIFICATION-TYPE
	OBJECTS { genericTrap }
	STATUS     current
	DESCRIPTION 
		"This trap is generated by Auot Recovery Feature
		                Trap Severity Level: Major."
	::= { systemTraps 28 }

-- =============================================================================
-- Definition of SNTP Traps Subgroup Objects : sntpTraps
-- ============================================================================= 

sntpFailure  NOTIFICATION-TYPE
	OBJECTS { genericTrap }
	STATUS     current
	DESCRIPTION 
		"This trap is generated when the SNTP fails to get the time from 
		 SNTP server. 
		Trap Severity Level: Major."
	::= { sntpTraps 1 }

-- =============================================================================
-- Definition of Image Traps Subgroup Objects : imageTraps
-- ============================================================================= 

invalidImage  NOTIFICATION-TYPE
	OBJECTS { genericTrap }
	STATUS     current
	DESCRIPTION 
		"This trap is generated when the image loaded is invalid or too 
		 large or incompatible. 
		Trap Severity Level: Major."
	::= { imageTraps 1 }

firmwareUpgradedSuccessfully  NOTIFICATION-TYPE
	OBJECTS { genericTrap }
	STATUS     current
	DESCRIPTION 
		"This trap is generated when the firmware image upgraded successfully. 
		Trap Severity Level: Informational."
	::= { imageTraps 2 }

pppoeIPAddress  NOTIFICATION-TYPE
	OBJECTS { genericTrap }
	STATUS     current
	DESCRIPTION 
		"This trap is generated whenever ppp interfaces comes up and IP Address can be seen here
		                Trap Severity Level: Major."
	::= { networkTraps 6 }

-- =============================================================================
-- Definition of TFTP Traps Subgroup Objects : tftpTraps
-- ============================================================================= 	

tftpFailedOperation  NOTIFICATION-TYPE
	OBJECTS { genericTrap }
	STATUS     current
	DESCRIPTION 
		"This trap is generated when a failure has occurred with the TFTP  
		operation. 
		Trap Severity Level: Major."
	::= { tftpTraps 1 }

tftpOperationInitiated  NOTIFICATION-TYPE
	OBJECTS { genericTrap }
	STATUS     current
	DESCRIPTION 
		"This trap is generated when a TFTP operation has been initiated. 
		Trap Severity Level: Informational."
	::= { tftpTraps 2 }

tftpOperationCompleted  NOTIFICATION-TYPE
	OBJECTS { genericTrap }
	STATUS     current
	DESCRIPTION 
		"This trap is generated when a TFTP operation has been completed. 
		Trap Severity Level: Informational."
	::= { tftpTraps 3 }

-- =============================================================================
-- Definition of WORP Traps Subgroup Objects : worpTraps
-- ============================================================================= 

worpStationRegister  NOTIFICATION-TYPE
	OBJECTS { genericTrap }
	STATUS     current
	DESCRIPTION 
		"This trap is generated when a WORP satellite has registered on 
		        an interface of a base.
		        Trap Severity Level: Informational."
	::= { worpTraps 1 }

worpStationDeregister  NOTIFICATION-TYPE
	OBJECTS { genericTrap }
	STATUS     current
	DESCRIPTION 
		"This trap is generated when a WORP satellite has been deRegistered  
		        from an interface of a base.  
		        Trap Severity Level: Informational."
	::= { worpTraps 2 }

worpErrorCountThresholdReached  NOTIFICATION-TYPE
	OBJECTS { genericTrap }
	STATUS     current
	DESCRIPTION 
		"This trap is generated by the BSU and SU WORP error  
		        counter reach user configurable threshold  
		    Trap Severity Level : Informational"
	::= { worpTraps 3 }

rssiDropThresholdReached  NOTIFICATION-TYPE
	OBJECTS { genericTrap }
	STATUS     current
	DESCRIPTION 
		"This trap is generated by the SU when either RSSI level drop  
		        is greater than user configurable threshold 
		    Trap Severity Level : Informational"
	::= { worpTraps 4 }

worpBSURegistrationStatus  NOTIFICATION-TYPE
	OBJECTS { genericTrap }
	STATUS     current
	DESCRIPTION 
		"This trap is generated by SU only when the Secondary BSU Name
		                is configured and while connecting any BSU.
		    Trap Severity Level : Informational"
	::= { worpTraps 5 }

-- =============================================================================
-- Definition of SpectrumAnalyzer Traps Subgroup Objects : spectrumAnalyzerTraps
-- ============================================================================= 

spectrumAnalyzerStartAndStop  NOTIFICATION-TYPE
	OBJECTS { genericTrap }
	STATUS     current
	DESCRIPTION 
		"This trap is generated when spectrumAnalyzer is Started and Stopped.
		         Trap Severity Level : Informational"
	::= { spectrumAnalyzerTraps 1 }

-- =============================================================================
-- Definition of Image Site Survey Subgroup Objects : siteSurvey
-- ============================================================================= 
-- Definition of Site Survey Operation Table Objects 

worpSiteSurveyOperationTable  OBJECT-TYPE
	SYNTAX SEQUENCE OF WorpSiteSurveyOperationTableEntry
	MAX-ACCESS not-accessible
	STATUS     current
	DESCRIPTION 
		"This table contains the information about all the BSU which all
		                 are visible for this SU."
	::= { worpSiteSurvey 1 }

worpSiteSurveyOperationTableEntry  OBJECT-TYPE
	SYNTAX 	WorpSiteSurveyOperationTableEntry
	MAX-ACCESS not-accessible
	STATUS     current
	DESCRIPTION 
		"This parameter represents the entry in the worpSiteSurvey operation table."
	INDEX { worpSiteSurveyOperationTableIndex }
	::= { worpSiteSurveyOperationTable 1 }

WorpSiteSurveyOperationTableEntry ::= SEQUENCE {
	worpSiteSurveyOperationTableIndex
		Unsigned32,
	worpSiteSurveyOperationIfName
		DisplayString,
	worpSiteSurveyOperationStatus
		INTEGER
}

worpSiteSurveyOperationTableIndex  OBJECT-TYPE
	SYNTAX     Unsigned32
	MAX-ACCESS read-only
	STATUS     current
	DESCRIPTION 
		"This parameter represents the index to the worpSiteSurveyOperationTable."
	::= { worpSiteSurveyOperationTableEntry 1 }

worpSiteSurveyOperationIfName  OBJECT-TYPE
	SYNTAX     DisplayString (SIZE(1..32))
	MAX-ACCESS read-only
	STATUS     current
	DESCRIPTION 
		"This parameter shows the wireless interface name for which site survey 
		                 parameters are shown."
	::= { worpSiteSurveyOperationTableEntry 2 }

worpSiteSurveyOperationStatus  OBJECT-TYPE
	SYNTAX     INTEGER {
		enable (1),
		disable (2)
	}
	MAX-ACCESS read-write
	STATUS     current
	DESCRIPTION 
		"This parameter is used enable/disable the site survey operation."
	::= { worpSiteSurveyOperationTableEntry 3 }

-- Definition of Site Survey Table Objects 

worpSiteSurveyTable  OBJECT-TYPE
	SYNTAX SEQUENCE OF WorpSiteSurveyTableEntry
	MAX-ACCESS not-accessible
	STATUS     current
	DESCRIPTION 
		"This table contains the information about all the BSU which all
		                 are visible for this SU."
	::= { worpSiteSurvey 2 }

worpSiteSurveyTableEntry  OBJECT-TYPE
	SYNTAX 	WorpSiteSurveyTableEntry
	MAX-ACCESS not-accessible
	STATUS     current
	DESCRIPTION 
		"This parameter represents the entry in the worpSiteSurvey table."
	INDEX { worpSiteSurveyTableIndex, 
		worpSiteSurveyTableSecIndex }
	::= { worpSiteSurveyTable 1 }

WorpSiteSurveyTableEntry ::= SEQUENCE {
	worpSiteSurveyTableIndex
		Unsigned32,
	worpSiteSurveyTableSecIndex
		Unsigned32,
	worpSiteSurveyBaseMACAddress
		PhysAddress,
	worpSiteSurveyBaseName
		DisplayString,
	worpSiteSurveyMaxSatellitesAllowed
		Unsigned32,
	worpSiteSurveyNumSatellitesRegistered
		Unsigned32,
	worpSiteSurveySatelliteRegisteredStatus
		INTEGER,
	worpSiteSurveyLocalTxRate
		Unsigned32,
	worpSiteSurveyRemoteTxRate
		Unsigned32,
	worpSiteSurveyLocalSignalLevel
		Integer32,
	worpSiteSurveyLocalNoiseLevel
		Integer32,
	worpSiteSurveyLocalSNR
		Unsigned32,
	worpSiteSurveyRemoteSignalLevel
		Integer32,
	worpSiteSurveyRemoteNoiseLevel
		Integer32,
	worpSiteSurveyRemoteSNR
		Unsigned32,
	worpSiteSurveyChannel
		Unsigned32,
	worpSiteSurveyChannelBandwidth
		Unsigned32,
	worpSiteSurveyChannelRxRate
		Unsigned32,
	worpSiteSurveyBaseBridgePort
		Unsigned32,
	worpSiteSurveyLocalMimoCtrlSig1
		Integer32,
	worpSiteSurveyLocalMimoCtrlSig2
		Integer32,
	worpSiteSurveyLocalMimoCtrlSig3
		Integer32,
	worpSiteSurveyLocalMimoNoise
		Integer32,
	worpSiteSurveyLocalMimoCtrlSNR1
		Unsigned32,
	worpSiteSurveyLocalMimoCtrlSNR2
		Unsigned32,
	worpSiteSurveyLocalMimoCtrlSNR3
		Unsigned32,
	worpSiteSurveyRemoteMimoCtrlSig1
		Integer32,
	worpSiteSurveyRemoteMimoCtrlSig2
		Integer32,
	worpSiteSurveyRemoteMimoCtrlSig3
		Integer32,
	worpSiteSurveyRemoteMimoNoise
		Integer32,
	worpSiteSurveyRemoteMimoCtrlSNR1
		Unsigned32,
	worpSiteSurveyRemoteMimoCtrlSNR2
		Unsigned32,
	worpSiteSurveyRemoteMimoCtrlSNR3
		Unsigned32,
	worpSiteSurveyLocalChainBalStatus
		INTEGER,
	worpSiteSurveyRemoteChainBalStatus
		INTEGER,
	worpSiteSurveyLocalMimoNoise1
		Integer32,
	worpSiteSurveyLocalMimoNoise2
		Integer32,
	worpSiteSurveyLocalMimoNoise3
		Integer32,
	worpSiteSurveyRemoteMimoNoise1
		Integer32,
	worpSiteSurveyRemoteMimoNoise2
		Integer32,
	worpSiteSurveyRemoteMimoNoise3
		Integer32,
	worpSiteSurveyRemoteWORPVersion
		Unsigned32,
	worpSiteSurveyActiveTPC
		Unsigned32,
	worpSiteSurveyActiveEIRP
		Unsigned32,
	worpSiteSurveyActivePower
		Unsigned32,
	worpSiteSurveyBaseDisconnect
		Integer32,
	worpSiteSurveyBasePort
		Unsigned32,
	worpSiteSurveySupportedRates
		OCTET STRING,
	worpSiteSurveyMinSNRInfo
		OCTET STRING,
	worpSiteSurveyMaxSNRInfo
		OCTET STRING,
	worpSiteSurveyOperationalMode
		INTEGER,
	worpSiteSurveyGuardInterval
		INTEGER,
	worpSiteSurveyLinkProfileIndex
		Unsigned32,
	worpSiteSurveyQoSClassIndex
		Unsigned32,
	worpSiteSurveyTxAntennas
		INTEGER,
	worpSiteSurveyDCSReTxPercentage
		Integer32,
	worpSiteSurveyBaseIP
		IpAddress
}

worpSiteSurveyTableIndex  OBJECT-TYPE
	SYNTAX     Unsigned32
	MAX-ACCESS read-only
	STATUS     current
	DESCRIPTION 
		"This parameter represents te index to the worpSiteSurveyTable."
	::= { worpSiteSurveyTableEntry 1 }

worpSiteSurveyTableSecIndex  OBJECT-TYPE
	SYNTAX     Unsigned32
	MAX-ACCESS read-only
	STATUS     current
	DESCRIPTION 
		"This parameter represents te index to the worpSiteSurveyTable."
	::= { worpSiteSurveyTableEntry 2 }

worpSiteSurveyBaseMACAddress  OBJECT-TYPE
	SYNTAX     PhysAddress
	MAX-ACCESS read-only
	STATUS     current
	DESCRIPTION 
		"This parameter represents the MAC address of the BSU."
	::= { worpSiteSurveyTableEntry 3 }

worpSiteSurveyBaseName  OBJECT-TYPE
	SYNTAX     DisplayString
	MAX-ACCESS read-only
	STATUS     current
	DESCRIPTION 
		"This parameter represents the name of the BSU."
	::= { worpSiteSurveyTableEntry 4 }

worpSiteSurveyMaxSatellitesAllowed  OBJECT-TYPE
	SYNTAX     Unsigned32
	MAX-ACCESS read-only
	STATUS     current
	DESCRIPTION 
		"This parameter represents the maximum number of satellites 
		                 allowed to register with this BSU."
	::= { worpSiteSurveyTableEntry 5 }

worpSiteSurveyNumSatellitesRegistered  OBJECT-TYPE
	SYNTAX     Unsigned32
	MAX-ACCESS read-only
	STATUS     current
	DESCRIPTION 
		"This parameter represents the number of satellites currently 
		                 registered on this BSU."
	::= { worpSiteSurveyTableEntry 6 }

worpSiteSurveySatelliteRegisteredStatus  OBJECT-TYPE
	SYNTAX     INTEGER {
		registered (1),
		not-Registered (2)
	}
	MAX-ACCESS read-only
	STATUS     current
	DESCRIPTION 
		"This parameter represents the registration status of this satellite on the BSU."
	::= { worpSiteSurveyTableEntry 7 }

worpSiteSurveyLocalTxRate  OBJECT-TYPE
	SYNTAX     Unsigned32
	MAX-ACCESS read-only
	STATUS     current
	DESCRIPTION 
		"This parameter represents the transmission rate of the SU. This field is not 
		                 valid if the registration status is Not-Registered"
	::= { worpSiteSurveyTableEntry 8 }

worpSiteSurveyRemoteTxRate  OBJECT-TYPE
	SYNTAX     Unsigned32
	MAX-ACCESS read-only
	STATUS     current
	DESCRIPTION 
		"This parameter represents the transmission rate of the BSU. This field is 
		                  not valid if the registration status is Not-Registered"
	::= { worpSiteSurveyTableEntry 9 }

worpSiteSurveyLocalSignalLevel  OBJECT-TYPE
	SYNTAX     Integer32
	MAX-ACCESS read-only
	STATUS     current
	DESCRIPTION 
		"This parameter displays the current signal level of the incoming wireless
		                 frames from this BSU."
	::= { worpSiteSurveyTableEntry 10 }

worpSiteSurveyLocalNoiseLevel  OBJECT-TYPE
	SYNTAX     Integer32
	MAX-ACCESS read-only
	STATUS     current
	DESCRIPTION 
		"This parameter displays the current noise level of the incoming wireless 
		                 frames from this BSU."
	::= { worpSiteSurveyTableEntry 11 }

worpSiteSurveyLocalSNR  OBJECT-TYPE
	SYNTAX     Unsigned32
	MAX-ACCESS read-only
	STATUS     current
	DESCRIPTION 
		"This parameter represents the current Local SNR."
	::= { worpSiteSurveyTableEntry 12 }

worpSiteSurveyRemoteSignalLevel  OBJECT-TYPE
	SYNTAX     Integer32
	MAX-ACCESS read-only
	STATUS     current
	DESCRIPTION 
		"This parameter displays the current signal level of the incoming wireless 
		                 frames at BSU. This field is not valid if the registration status is 
		                 Not-Registered"
	::= { worpSiteSurveyTableEntry 13 }

worpSiteSurveyRemoteNoiseLevel  OBJECT-TYPE
	SYNTAX     Integer32
	MAX-ACCESS read-only
	STATUS     current
	DESCRIPTION 
		"This parameter displays  the current noise level of the incoming wireless 
		                 frames at BSU. This field is not valid if the registration status is 
		                 Not-Registered."
	::= { worpSiteSurveyTableEntry 14 }

worpSiteSurveyRemoteSNR  OBJECT-TYPE
	SYNTAX     Unsigned32
	MAX-ACCESS read-only
	STATUS     current
	DESCRIPTION 
		"This parameter represents the current SNR at BSU. This field is not valid
		                if the registration status is Not-Registered"
	::= { worpSiteSurveyTableEntry 15 }

worpSiteSurveyChannel  OBJECT-TYPE
	SYNTAX     Unsigned32
	MAX-ACCESS read-only
	STATUS     current
	DESCRIPTION 
		"This parameter represents the channel at which the BSU is operating."
	::= { worpSiteSurveyTableEntry 16 }

worpSiteSurveyChannelBandwidth  OBJECT-TYPE
	SYNTAX     Unsigned32
	MAX-ACCESS read-only
	STATUS     current
	DESCRIPTION 
		"This parameter represents the BSU channel bandwidth."
	::= { worpSiteSurveyTableEntry 17 }

worpSiteSurveyChannelRxRate  OBJECT-TYPE
	SYNTAX     Unsigned32
	MAX-ACCESS read-only
	STATUS     current
	DESCRIPTION 
		"This parameter represents the Rx rate of BSU."
	::= { worpSiteSurveyTableEntry 18 }

worpSiteSurveyBaseBridgePort  OBJECT-TYPE
	SYNTAX     Unsigned32
	MAX-ACCESS read-only
	STATUS     current
	DESCRIPTION 
		"This parameter represents the SU's Bridge port for which BSU is connected."
	::= { worpSiteSurveyTableEntry 19 }

worpSiteSurveyLocalMimoCtrlSig1  OBJECT-TYPE
	SYNTAX     Integer32
	MAX-ACCESS read-only
	STATUS     current
	DESCRIPTION 
		"This parameter represents the Rx rate of BSU."
	::= { worpSiteSurveyTableEntry 20 }

worpSiteSurveyLocalMimoCtrlSig2  OBJECT-TYPE
	SYNTAX     Integer32
	MAX-ACCESS read-only
	STATUS     current
	DESCRIPTION 
		"This parameter represents the Rx rate of BSU."
	::= { worpSiteSurveyTableEntry 21 }

worpSiteSurveyLocalMimoCtrlSig3  OBJECT-TYPE
	SYNTAX     Integer32
	MAX-ACCESS read-only
	STATUS     current
	DESCRIPTION 
		"This parameter represents the Rx rate of BSU."
	::= { worpSiteSurveyTableEntry 22 }

worpSiteSurveyLocalMimoNoise  OBJECT-TYPE
	SYNTAX     Integer32
	MAX-ACCESS read-only
	STATUS     current
	DESCRIPTION 
		"This parameter represents the Rx rate of BSU."
	::= { worpSiteSurveyTableEntry 23 }

worpSiteSurveyLocalMimoCtrlSNR1  OBJECT-TYPE
	SYNTAX     Unsigned32
	MAX-ACCESS read-only
	STATUS     current
	DESCRIPTION 
		"This parameter represents the Rx rate of BSU."
	::= { worpSiteSurveyTableEntry 24 }

worpSiteSurveyLocalMimoCtrlSNR2  OBJECT-TYPE
	SYNTAX     Unsigned32
	MAX-ACCESS read-only
	STATUS     current
	DESCRIPTION 
		"This parameter represents the Rx rate of BSU."
	::= { worpSiteSurveyTableEntry 25 }

worpSiteSurveyLocalMimoCtrlSNR3  OBJECT-TYPE
	SYNTAX     Unsigned32
	MAX-ACCESS read-only
	STATUS     current
	DESCRIPTION 
		"This parameter represents the Rx rate of BSU."
	::= { worpSiteSurveyTableEntry 26 }

worpSiteSurveyRemoteMimoCtrlSig1  OBJECT-TYPE
	SYNTAX     Integer32
	MAX-ACCESS read-only
	STATUS     current
	DESCRIPTION 
		"This parameter represents the Rx rate of BSU."
	::= { worpSiteSurveyTableEntry 27 }

worpSiteSurveyRemoteMimoCtrlSig2  OBJECT-TYPE
	SYNTAX     Integer32
	MAX-ACCESS read-only
	STATUS     current
	DESCRIPTION 
		"This parameter represents the Rx rate of BSU."
	::= { worpSiteSurveyTableEntry 28 }

worpSiteSurveyRemoteMimoCtrlSig3  OBJECT-TYPE
	SYNTAX     Integer32
	MAX-ACCESS read-only
	STATUS     current
	DESCRIPTION 
		"This parameter represents the Rx rate of BSU."
	::= { worpSiteSurveyTableEntry 29 }

worpSiteSurveyRemoteMimoNoise  OBJECT-TYPE
	SYNTAX     Integer32
	MAX-ACCESS read-only
	STATUS     current
	DESCRIPTION 
		"This parameter represents the Rx rate of BSU."
	::= { worpSiteSurveyTableEntry 30 }

worpSiteSurveyRemoteMimoCtrlSNR1  OBJECT-TYPE
	SYNTAX     Unsigned32
	MAX-ACCESS read-only
	STATUS     current
	DESCRIPTION 
		"This parameter represents the Rx rate of BSU."
	::= { worpSiteSurveyTableEntry 31 }

worpSiteSurveyRemoteMimoCtrlSNR2  OBJECT-TYPE
	SYNTAX     Unsigned32
	MAX-ACCESS read-only
	STATUS     current
	DESCRIPTION 
		"This parameter represents the Rx rate of BSU."
	::= { worpSiteSurveyTableEntry 32 }

worpSiteSurveyRemoteMimoCtrlSNR3  OBJECT-TYPE
	SYNTAX     Unsigned32
	MAX-ACCESS read-only
	STATUS     current
	DESCRIPTION 
		"This parameter represents the Rx rate of BSU."
	::= { worpSiteSurveyTableEntry 33 }

worpSiteSurveyLocalChainBalStatus  OBJECT-TYPE
	SYNTAX     INTEGER {
		notApplicable (1),
		balanced (2),
		notBalanced (3)
	}
	MAX-ACCESS read-only
	STATUS     current
	DESCRIPTION 
		"When this parameter indicates the local chain balance status."
	::= { worpSiteSurveyTableEntry 34 }

worpSiteSurveyRemoteChainBalStatus  OBJECT-TYPE
	SYNTAX     INTEGER {
		notApplicable (1),
		balanced (2),
		notBalanced (3)
	}
	MAX-ACCESS read-only
	STATUS     current
	DESCRIPTION 
		"When this parameter indicates the remote chain balance status."
	::= { worpSiteSurveyTableEntry 35 }

worpSiteSurveyLocalMimoNoise1  OBJECT-TYPE
	SYNTAX     Integer32
	MAX-ACCESS read-only
	STATUS     current
	DESCRIPTION 
		""
	::= { worpSiteSurveyTableEntry 36 }

worpSiteSurveyLocalMimoNoise2  OBJECT-TYPE
	SYNTAX     Integer32
	MAX-ACCESS read-only
	STATUS     current
	DESCRIPTION 
		""
	::= { worpSiteSurveyTableEntry 37 }

worpSiteSurveyLocalMimoNoise3  OBJECT-TYPE
	SYNTAX     Integer32
	MAX-ACCESS read-only
	STATUS     current
	DESCRIPTION 
		""
	::= { worpSiteSurveyTableEntry 38 }

worpSiteSurveyRemoteMimoNoise1  OBJECT-TYPE
	SYNTAX     Integer32
	MAX-ACCESS read-only
	STATUS     current
	DESCRIPTION 
		""
	::= { worpSiteSurveyTableEntry 39 }

worpSiteSurveyRemoteMimoNoise2  OBJECT-TYPE
	SYNTAX     Integer32
	MAX-ACCESS read-only
	STATUS     current
	DESCRIPTION 
		""
	::= { worpSiteSurveyTableEntry 40 }

worpSiteSurveyRemoteMimoNoise3  OBJECT-TYPE
	SYNTAX     Integer32
	MAX-ACCESS read-only
	STATUS     current
	DESCRIPTION 
		""
	::= { worpSiteSurveyTableEntry 41 }

worpSiteSurveyRemoteWORPVersion  OBJECT-TYPE
	SYNTAX     Unsigned32
	MAX-ACCESS read-only
	STATUS     current
	DESCRIPTION 
		"This parameter represents the Rx rate of BSU."
	::= { worpSiteSurveyTableEntry 42 }

worpSiteSurveyActiveTPC  OBJECT-TYPE
	SYNTAX     Unsigned32
	MAX-ACCESS read-only
	STATUS     current
	DESCRIPTION 
		"This parameter provides the information about the current TPC.
		 Obtained value divided by 2 gives the TPC."
	::= { worpSiteSurveyTableEntry 43 }

worpSiteSurveyActiveEIRP  OBJECT-TYPE
	SYNTAX     Unsigned32
	MAX-ACCESS read-only
	STATUS     current
	DESCRIPTION 
		"This parameter provides the information about the current EIRP.
		 Obtained value divided by 2 gives the EIRP."
	::= { worpSiteSurveyTableEntry 44 }

worpSiteSurveyActivePower  OBJECT-TYPE
	SYNTAX     Unsigned32
	MAX-ACCESS read-only
	STATUS     current
	DESCRIPTION 
		"This parameter provides the information about the current Power.
		 Obtained value divided by 2 gives the Power."
	::= { worpSiteSurveyTableEntry 45 }

worpSiteSurveyBaseDisconnect  OBJECT-TYPE
	SYNTAX     Integer32
	MAX-ACCESS read-write
	STATUS     current
	DESCRIPTION 
		"This parameter is used to disconnect the Base."
	::= { worpSiteSurveyTableEntry 46 }

worpSiteSurveyBasePort  OBJECT-TYPE
	SYNTAX     Unsigned32
	MAX-ACCESS read-only
	STATUS     current
	DESCRIPTION 
		"This parameter represents the SU's port for which BSU is connected."
	::= { worpSiteSurveyTableEntry 47 }

worpSiteSurveySupportedRates  OBJECT-TYPE
	SYNTAX     OCTET STRING
	MAX-ACCESS read-only
	STATUS     current
	DESCRIPTION 
		"This parameter represents the supported data rates for this BSU."
	::= { worpSiteSurveyTableEntry 48 }

worpSiteSurveyMinSNRInfo  OBJECT-TYPE
	SYNTAX     OCTET STRING
	MAX-ACCESS read-only
	STATUS     current
	DESCRIPTION 
		"This parameter represents the Minimum SNR Table for this BSU."
	::= { worpSiteSurveyTableEntry 49 }

worpSiteSurveyMaxSNRInfo  OBJECT-TYPE
	SYNTAX     OCTET STRING
	MAX-ACCESS read-only
	STATUS     current
	DESCRIPTION 
		"This parameter represents the Maximum SNR Table for this BSU."
	::= { worpSiteSurveyTableEntry 50 }

worpSiteSurveyOperationalMode  OBJECT-TYPE
	SYNTAX     INTEGER {
		highThroughput (1),
		legacy (2)
	}
	MAX-ACCESS read-only
	STATUS     current
	DESCRIPTION 
		"This parameter represents the device operation mode."
	::= { worpSiteSurveyTableEntry 51 }

worpSiteSurveyGuardInterval  OBJECT-TYPE
	SYNTAX     INTEGER {
		shortGI-400nSec (1),
		fullGI-800nSec (2)
	}
	MAX-ACCESS read-only
	STATUS     current
	DESCRIPTION 
		"This parameter represents the device Guard Interval."
	::= { worpSiteSurveyTableEntry 52 }

worpSiteSurveyLinkProfileIndex  OBJECT-TYPE
	SYNTAX     Unsigned32
	MAX-ACCESS read-only
	STATUS     current
	DESCRIPTION 
		"This parameter represents the link profile index for this BSU."
	::= { worpSiteSurveyTableEntry 53 }

worpSiteSurveyQoSClassIndex  OBJECT-TYPE
	SYNTAX     Unsigned32
	MAX-ACCESS read-only
	STATUS     current
	DESCRIPTION 
		"This parameter represents the qos class index for this BSU."
	::= { worpSiteSurveyTableEntry 54 }

worpSiteSurveyTxAntennas  OBJECT-TYPE
	SYNTAX     INTEGER {
		one (1),
		two (2),
		three (3),
		four (4),
		five (5),
		six (6),
		seven (7)
	}
	MAX-ACCESS read-only
	STATUS     current
	DESCRIPTION 
		"This parameter represents the Tx Antenna chain mask. This is represented as bitmask.
		         Eg: 3 - 011 (binary value) - first and second antennas are enabled. 
		             7 - 111 (binary value) - all three are enabled."
	::= { worpSiteSurveyTableEntry 55 }

worpSiteSurveyDCSReTxPercentage  OBJECT-TYPE
	SYNTAX     Integer32 (0..100)
	MAX-ACCESS read-only
	STATUS     current
	DESCRIPTION 
		" This Parameter represents the DCS Re Tx percentage of this BSU. "
	::= { worpSiteSurveyTableEntry 56 }

worpSiteSurveyBaseIP OBJECT-TYPE
        SYNTAX      IpAddress
        MAX-ACCESS  read-only
        STATUS      current
        DESCRIPTION "This parameter represents the IP address of the BSU."
        ::= { worpSiteSurveyTableEntry 57 }

-- =============================================================================
-- The Temperature Log  Subgroup: Temperature 
-- =============================================================================

currentUnitTemp  OBJECT-TYPE
	SYNTAX     Integer32 (-40..60)
	MAX-ACCESS read-only
	STATUS     current
	DESCRIPTION 
		"This parameter is used for the internal unit temperature in degrees
		    celsius. The range of the temperature is -30 to 60 degrees celsius."
	::= { temperature 1 }

highTempThreshold  OBJECT-TYPE
	SYNTAX     Integer32 (-40..60)
	MAX-ACCESS read-write
	STATUS     current
	DESCRIPTION 
		"This parameter is used set the high temperature threshold by the user."
	DEFVAL  { 60 }
	::= { temperature 2 }

lowTempThreshold  OBJECT-TYPE
	SYNTAX     Integer32 (-40..60)
	MAX-ACCESS read-write
	STATUS     current
	DESCRIPTION 
		"This parameter is used set the low temperature threshold by the user."
	DEFVAL  { -40 }
	::= { temperature 3 }

tempLoggingInterval  OBJECT-TYPE
	SYNTAX     Integer32 (1..60)
	MAX-ACCESS read-write
	STATUS     current
	DESCRIPTION 
		"This parameter is used for logging interval. The valid values  
		    are 1,5,10,15,20,25,30,35,40,45,50,55,and 60."
	DEFVAL  { 5 }
	::= { temperature 4 }

tempLogReset  OBJECT-TYPE
	SYNTAX     INTEGER {
		yes (1),
		no (2)
	}
	MAX-ACCESS read-write
	STATUS     current
	DESCRIPTION 
		"This parameter is used for reset/clear the temperature log."
	DEFVAL  { no }
	::= { temperature 5 }

-- =============================================================================
-- The System Monitoring Subgroup: sysMonitor 
-- =============================================================================
-- CPU usage

sysMonitorCPUUsage  OBJECT-TYPE
	SYNTAX     DisplayString (SIZE(1..32))
	MAX-ACCESS read-only
	STATUS     deprecated
	DESCRIPTION 
		"This parameter has depricated, refer the OID 1.3.6.1.2.1.25.3.3.1.2 for CPU usage."
	::= { sysMonitor 1 }

-- RAM usage

sysMonitorRAMUsage  OBJECT-TYPE
	SYNTAX     DisplayString (SIZE(1..32))
	MAX-ACCESS read-only
	STATUS     current
	DESCRIPTION 
		"This parameter shows the present percentage RAM usage."
	::= { sysMonitor 2 }

-- LED

sysMonLEDStackGlowBitmap  OBJECT-TYPE
	SYNTAX     Integer32
	MAX-ACCESS read-only
	STATUS     current
	DESCRIPTION 
		"This parameter represents the bit map for the LEDs to be glow. The value of is interpreted as a bit field to glow the respective LED in LED Stack.
		                   
		                   Blinking   = -1,
		                   LEDs off   = 0
		                   First LED  = 1,
		                   First & Second LED = 3,
		                   First, Second & Third LED  = 7,
		                   First, Second, Third & Fourth LED = 15,
		                   First, Second, Third, Fourth & Fifth LED  = 31."
	::= { sysMonLEDStack 1 }

-- Sync LED

sysMonLEDSyncGlow  OBJECT-TYPE
	SYNTAX     Integer32
	MAX-ACCESS read-only
	STATUS     current
	DESCRIPTION 
		"This parameter represents the Sync LED status.
		       -1  = Async mode (OFF) 
		       0   = LED operation not applicable (OFF) 
		       1   = Time Slot synchronized autonomously in BSU (Blinking)
		       2   = Time Slot synchronized by GPS in BSU (ON)
		       3   = Time Slot synchronized by Announcement in SU (ON)
		       4,5 = Time Slot went out of Sync in BSU or SU (OFF)"
	::= { sysMonLEDStack 2 }

-- =============================================================================
-- The System Monitoring Subgroup: igmpStats
-- =============================================================================
-- =============================================================================
-- The IGMP Stats Subgroup: igmpEthernetSnoopingStats
-- =============================================================================
-- Ethernet 1 IGMP Multicast Group Table

igmpEth1MCastTable  OBJECT-TYPE
	SYNTAX SEQUENCE OF IgmpEth1MCastTableEntry
	MAX-ACCESS not-accessible
	STATUS     current
	DESCRIPTION 
		"This table holds the IGMP multicast IP and MAC address details for 
		                 the ethernet interface 1"
	::= { igmpEthernetSnoopingStats 1 }

igmpEth1MCastTableEntry  OBJECT-TYPE
	SYNTAX 	IgmpEth1MCastTableEntry
	MAX-ACCESS not-accessible
	STATUS     current
	DESCRIPTION 
		"This parameter represents the entry for this table."
	INDEX { igmpEth1MCastTableIndex }
	::= { igmpEth1MCastTable 1 }

IgmpEth1MCastTableEntry ::= SEQUENCE {
	igmpEth1MCastTableIndex
		Unsigned32,
	igmpEth1MCastGrpIp
		IpAddress,
	igmpEth1MCastGrpMACAddr
		MacAddress,
	igmpEth1MCastGrpAgingTimeElapsed
		TimeTicks
}

igmpEth1MCastTableIndex  OBJECT-TYPE
	SYNTAX     Unsigned32
	MAX-ACCESS read-only
	STATUS     current
	DESCRIPTION 
		"This parameter represents the index for this table."
	::= { igmpEth1MCastTableEntry 1 }

igmpEth1MCastGrpIp  OBJECT-TYPE
	SYNTAX     IpAddress
	MAX-ACCESS read-only
	STATUS     current
	DESCRIPTION 
		"This parameter indicates the IP multicast address of ethernet interface 1
		                 learned by IGMP snooping."
	::= { igmpEth1MCastTableEntry 2 }

igmpEth1MCastGrpMACAddr  OBJECT-TYPE
	SYNTAX     MacAddress
	MAX-ACCESS read-only
	STATUS     current
	DESCRIPTION 
		"This parameter indicates the Mac multicast address of ethernet interface 1
		                 learned by IGMP snooping."
	::= { igmpEth1MCastTableEntry 3 }

igmpEth1MCastGrpAgingTimeElapsed  OBJECT-TYPE
	SYNTAX     TimeTicks
	MAX-ACCESS read-only
	STATUS     current
	DESCRIPTION 
		"This parameter specifies the aging time for multicast entries for the ethernet
		                 interface 1."
	::= { igmpEth1MCastTableEntry 4 }

-- Ethernet 2 IGMP Multicast Group Table

igmpEth2MCastTable  OBJECT-TYPE
	SYNTAX SEQUENCE OF IgmpEth2MCastTableEntry
	MAX-ACCESS not-accessible
	STATUS     current
	DESCRIPTION 
		"This table holds the IGMP multicast IP and MAC address details for 
		                 the ethernet interface 2"
	::= { igmpEthernetSnoopingStats 2 }

igmpEth2MCastTableEntry  OBJECT-TYPE
	SYNTAX 	IgmpEth2MCastTableEntry
	MAX-ACCESS not-accessible
	STATUS     current
	DESCRIPTION 
		"This parameter represents the entry for this table."
	INDEX { igmpEth2MCastTableIndex }
	::= { igmpEth2MCastTable 1 }

IgmpEth2MCastTableEntry ::= SEQUENCE {
	igmpEth2MCastTableIndex
		Unsigned32,
	igmpEth2MCastGrpIp
		IpAddress,
	igmpEth2MCastGrpMACAddr
		MacAddress,
	igmpEth2MCastGrpAgingTimeElapsed
		TimeTicks
}

igmpEth2MCastTableIndex  OBJECT-TYPE
	SYNTAX     Unsigned32
	MAX-ACCESS read-only
	STATUS     current
	DESCRIPTION 
		"This parameter represents the index for this table."
	::= { igmpEth2MCastTableEntry 1 }

igmpEth2MCastGrpIp  OBJECT-TYPE
	SYNTAX     IpAddress
	MAX-ACCESS read-only
	STATUS     current
	DESCRIPTION 
		"This parameter indicates the IP multicast address of ethernet interface 2
		                 learned by IGMP snooping."
	::= { igmpEth2MCastTableEntry 2 }

igmpEth2MCastGrpMACAddr  OBJECT-TYPE
	SYNTAX     MacAddress
	MAX-ACCESS read-only
	STATUS     current
	DESCRIPTION 
		"This parameter indicates the Mac multicast address of ethernet interface 2
		                 learned by IGMP snooping."
	::= { igmpEth2MCastTableEntry 3 }

igmpEth2MCastGrpAgingTimeElapsed  OBJECT-TYPE
	SYNTAX     TimeTicks
	MAX-ACCESS read-only
	STATUS     current
	DESCRIPTION 
		"This parameter specifies the aging time for multicast entries for the ethernet
		                 interface 2."
	::= { igmpEth2MCastTableEntry 4 }

-- =============================================================================
-- The IGMP Stats Subgroup: igmpWirelessSnoopingStats
-- =============================================================================
-- Wireless 1 IGMP Multicast Group Table

igmpWireless1MCastTable  OBJECT-TYPE
	SYNTAX SEQUENCE OF IgmpWireless1MCastTableEntry
	MAX-ACCESS not-accessible
	STATUS     current
	DESCRIPTION 
		"This table holds the IGMP multicast IP and MAC address details for 
		                 the wireless interface 1."
	::= { igmpWirelessSnoopingStats 1 }

igmpWireless1MCastTableEntry  OBJECT-TYPE
	SYNTAX 	IgmpWireless1MCastTableEntry
	MAX-ACCESS not-accessible
	STATUS     current
	DESCRIPTION 
		"This parameter represents the entry for the wireless multicast table."
	INDEX { igmpWireless1MCastTableIndex }
	::= { igmpWireless1MCastTable 1 }

IgmpWireless1MCastTableEntry ::= SEQUENCE {
	igmpWireless1MCastTableIndex
		Unsigned32,
	igmpWireless1MCastGrpIp
		IpAddress,
	igmpWireless1MCastGrpMACAddr
		MacAddress,
	igmpWireless1MCastGrpAgingTimeElapsed
		TimeTicks
}

igmpWireless1MCastTableIndex  OBJECT-TYPE
	SYNTAX     Unsigned32
	MAX-ACCESS read-only
	STATUS     current
	DESCRIPTION 
		"This parameter represents the index for this table."
	::= { igmpWireless1MCastTableEntry 1 }

igmpWireless1MCastGrpIp  OBJECT-TYPE
	SYNTAX     IpAddress
	MAX-ACCESS read-only
	STATUS     current
	DESCRIPTION 
		"This parameter indicates the IP multicast address of wireless interface 1
		                 learned by IGMP snooping."
	::= { igmpWireless1MCastTableEntry 2 }

igmpWireless1MCastGrpMACAddr  OBJECT-TYPE
	SYNTAX     MacAddress
	MAX-ACCESS read-only
	STATUS     current
	DESCRIPTION 
		"This parameter indicates the Mac multicast address of wireless interface 1
		                 learned by IGMP snooping."
	::= { igmpWireless1MCastTableEntry 3 }

igmpWireless1MCastGrpAgingTimeElapsed  OBJECT-TYPE
	SYNTAX     TimeTicks
	MAX-ACCESS read-only
	STATUS     current
	DESCRIPTION 
		"This parameter specifies the aging time for multicast entries for the wireless
		                 interface 1."
	::= { igmpWireless1MCastTableEntry 4 }

-- Igmp Router Port list Table

igmpRouterPortListTable  OBJECT-TYPE
	SYNTAX SEQUENCE OF IgmpRouterPortListTableEntry
	MAX-ACCESS not-accessible
	STATUS     current
	DESCRIPTION 
		"This table shows the IGMP router port stats for all interfaces."
	::= { igmpStats 3 }

igmpRouterPortListTableEntry  OBJECT-TYPE
	SYNTAX 	IgmpRouterPortListTableEntry
	MAX-ACCESS not-accessible
	STATUS     current
	DESCRIPTION 
		"This parameter represents the entry for the router port list table."
	INDEX { igmpRouterPortListTableIndex }
	::= { igmpRouterPortListTable 1 }

IgmpRouterPortListTableEntry ::= SEQUENCE {
	igmpRouterPortListTableIndex
		Unsigned32,
	igmpRouterPortNumber
		Unsigned32,
	igmpRouterAgingTimeElapsed
		TimeTicks
}

igmpRouterPortListTableIndex  OBJECT-TYPE
	SYNTAX     Unsigned32
	MAX-ACCESS read-only
	STATUS     current
	DESCRIPTION 
		"This paramter represents the interface number or index to 
		                   this table."
	::= { igmpRouterPortListTableEntry 1 }

igmpRouterPortNumber  OBJECT-TYPE
	SYNTAX     Unsigned32
	MAX-ACCESS read-only
	STATUS     current
	DESCRIPTION 
		"This parameter represents the router port number on which IGMP 
		                 snooping/listening is done."
	::= { igmpRouterPortListTableEntry 2 }

igmpRouterAgingTimeElapsed  OBJECT-TYPE
	SYNTAX     TimeTicks
	MAX-ACCESS read-only
	STATUS     current
	DESCRIPTION 
		"This parameter represents the time elapsed since snooping is started
		                 on the router port."
	::= { igmpRouterPortListTableEntry 3 }

-- ======================================================================================
-- Definition of the Eventlog Group objects : debuglog
-- ======================================================================================
-- debuglog bitmask 

debugLogBitMask  OBJECT-TYPE
	SYNTAX     Unsigned32
	MAX-ACCESS read-write
	STATUS     current
	DESCRIPTION 
		"This parameter specifies which debug levels are enabled. 
		 It is Bit Mask field. Bits are defined as follows 
		Bit0 - WORP general debug level. 
		Bit1 - DDRS debug level one. 
		Bit2 - DDRS debug level two. 
		Bit3 - DDRS debug level three."
	::= { debugLog 1 }

debugLogReset  OBJECT-TYPE
	SYNTAX     INTEGER {
		yes (1),
		no (2)
	}
	MAX-ACCESS read-write
	STATUS     current
	DESCRIPTION 
		"This parameter is used to reset/clear the debug log messages. 
		 When this parameter is set, then all enteries in the event log table 
		 are deleted/cleared. Select (1) to reset the table. 
		 "
	DEFVAL  { no }
	::= { debugLog 2 }

debugLogSize  OBJECT-TYPE
	SYNTAX     Unsigned32
	MAX-ACCESS read-only
	STATUS     current
	DESCRIPTION 
		"This parameter represents number line present in the debuglog file."
	::= { debugLog 3 }

-- =============================================================================
-- The System Monitoring Subgroup: scanDevices
-- =============================================================================

deviceScanStatus  OBJECT-TYPE
	SYNTAX     INTEGER {
		scanRequired (1),
		scanDone (2)
	}
	MAX-ACCESS read-write
	STATUS     current
	DESCRIPTION 
		"TBD."
	::= { scanDevices 1 }

-- Scan Device Table

scanDeviceTable  OBJECT-TYPE
	SYNTAX SEQUENCE OF ScanDeviceTableEntry
	MAX-ACCESS not-accessible
	STATUS     current
	DESCRIPTION 
		"This table holds the IGMP multicast IP and MAC address details for 
		                 the ethernet interface 1"
	::= { scanDevices 2 }

scanDeviceTableEntry  OBJECT-TYPE
	SYNTAX 	ScanDeviceTableEntry
	MAX-ACCESS not-accessible
	STATUS     current
	DESCRIPTION 
		"This parameter represents the entry for this table."
	INDEX { scanDeviceTableIndex }
	::= { scanDeviceTable 1 }

ScanDeviceTableEntry ::= SEQUENCE {
	scanDeviceTableIndex
		Unsigned32,
	scanDeviceName
		DisplayString,
	scanDeviceDescription
		DisplayString,
	scanDeviceMACAddress
		MacAddress,
	scanDeviceIPAddress
		IpAddress,
	scanDeviceIPMask
		IpAddress,
	scanDeviceDefaultRoute
		IpAddress,
	scanDeviceIPType
		INTEGER,
	scanDeviceUPTime
		TimeTicks,
	scanDeviceSNMPCommunity
		DisplayString,
	scanDeviceInetAddress
		InetAddress,
	scanDeviceInetDefaultGateway
		InetAddress
}

scanDeviceTableIndex  OBJECT-TYPE
	SYNTAX     Unsigned32
	MAX-ACCESS read-only
	STATUS     current
	DESCRIPTION 
		"TBD."
	::= { scanDeviceTableEntry 1 }

scanDeviceName  OBJECT-TYPE
	SYNTAX     DisplayString
	MAX-ACCESS read-only
	STATUS     current
	DESCRIPTION 
		"TBD."
	::= { scanDeviceTableEntry 2 }

scanDeviceDescription  OBJECT-TYPE
	SYNTAX     DisplayString
	MAX-ACCESS read-only
	STATUS     current
	DESCRIPTION 
		"TBD."
	::= { scanDeviceTableEntry 3 }

scanDeviceMACAddress  OBJECT-TYPE
	SYNTAX     MacAddress
	MAX-ACCESS read-only
	STATUS     current
	DESCRIPTION 
		"TBD."
	::= { scanDeviceTableEntry 4 }

scanDeviceIPAddress  OBJECT-TYPE
	SYNTAX     IpAddress
	MAX-ACCESS read-only
	STATUS     current
	DESCRIPTION 
		"TBD."
	::= { scanDeviceTableEntry 5 }

scanDeviceIPMask  OBJECT-TYPE
	SYNTAX     IpAddress
	MAX-ACCESS read-only
	STATUS     current
	DESCRIPTION 
		"TBD."
	::= { scanDeviceTableEntry 6 }

scanDeviceDefaultRoute  OBJECT-TYPE
	SYNTAX     IpAddress
	MAX-ACCESS read-only
	STATUS     current
	DESCRIPTION 
		"TBD."
	::= { scanDeviceTableEntry 7 }

scanDeviceIPType  OBJECT-TYPE
	SYNTAX     INTEGER {
		static (1),
		dynamic (2)
	}
	MAX-ACCESS read-only
	STATUS     current
	DESCRIPTION 
		"TBD."
	::= { scanDeviceTableEntry 8 }

scanDeviceUPTime  OBJECT-TYPE
	SYNTAX     TimeTicks
	MAX-ACCESS read-only
	STATUS     current
	DESCRIPTION 
		"TBD."
	::= { scanDeviceTableEntry 9 }

scanDeviceSNMPCommunity  OBJECT-TYPE
	SYNTAX     DisplayString
	MAX-ACCESS read-only
	STATUS     current
	DESCRIPTION 
		"TBD."
	::= { scanDeviceTableEntry 10 }

scanDeviceInetAddress  OBJECT-TYPE
	SYNTAX     InetAddress
	MAX-ACCESS read-only
	STATUS     current
	DESCRIPTION 
		"TBD."
	::= { scanDeviceTableEntry 11 }

scanDeviceInetDefaultGateway  OBJECT-TYPE
	SYNTAX     InetAddress
	MAX-ACCESS read-only
	STATUS     current
	DESCRIPTION 
		"TBD."
	::= { scanDeviceTableEntry 12 }

scanIPMode  OBJECT-TYPE
	SYNTAX     INTEGER {
		ipv4 (1),
		ipv6 (2)
	}
	MAX-ACCESS read-write
	STATUS     current
	DESCRIPTION 
		"TBD."
	::= { scanDevices 3 }

-- =============================================================================
-- The System Monitoring Subgroup: activeVLAN 
-- =============================================================================

activeVLANStatus  OBJECT-TYPE
	SYNTAX     INTEGER {
		enable (1),
		disable (2)
	}
	MAX-ACCESS read-only
	STATUS     current
	DESCRIPTION 
		"TBD."
	DEFVAL  { disable }
	::= { activeVLAN 1 }

activeMgmtVLANIdentifier  OBJECT-TYPE
	SYNTAX     VlanId
	MAX-ACCESS read-only
	STATUS     current
	DESCRIPTION 
		"TBD."
	DEFVAL  { -1 }
	::= { activeVLAN 2 }

activeMgmtVLANPriority  OBJECT-TYPE
	SYNTAX     Unsigned32 (0..7)
	MAX-ACCESS read-only
	STATUS     current
	DESCRIPTION 
		"TBD."
	DEFVAL  { 0 }
	::= { activeVLAN 3 }

activeVLANConfig  OBJECT-TYPE
	SYNTAX     INTEGER {
		local (1),
		remote (2)
	}
	MAX-ACCESS read-only
	STATUS     current
	DESCRIPTION 
		"TBD."
	DEFVAL  { local }
	::= { activeVLAN 4 }

activeQinQStatus  OBJECT-TYPE
	SYNTAX     INTEGER {
		enable (1),
		disable (2)
	}
	MAX-ACCESS read-only
	STATUS     current
	DESCRIPTION 
		"TBD."
	::= { activeVLAN 5 }

activeTpid  OBJECT-TYPE
	SYNTAX     INTEGER {
		x8100 (1),
		x9100 (2),
		x88a8 (3)
	}
	MAX-ACCESS read-only
	STATUS     current
	DESCRIPTION 
		"TBD."
	::= { activeVLAN 6 }

activeServiceProviderVLANId  OBJECT-TYPE
	SYNTAX     VlanId
	MAX-ACCESS read-only
	STATUS     current
	DESCRIPTION 
		"TBD."
	DEFVAL  { 0 }
	::= { activeVLAN 7 }

activeServiceProviderVLANPriority  OBJECT-TYPE
	SYNTAX     Unsigned32 (0..7)
	MAX-ACCESS read-only
	STATUS     current
	DESCRIPTION 
		"TBD."
	DEFVAL  { 0 }
	::= { activeVLAN 8 }

-- Active VLAN Ethernet Monitoring table

activeVLANEthMonTable  OBJECT-TYPE
	SYNTAX SEQUENCE OF ActiveVLANEthMonTableEntry
	MAX-ACCESS not-accessible
	STATUS     current
	DESCRIPTION 
		""
	::= { activeVLAN 9 }

activeVLANEthMonTableEntry  OBJECT-TYPE
	SYNTAX 	ActiveVLANEthMonTableEntry
	MAX-ACCESS not-accessible
	STATUS     current
	DESCRIPTION 
		"This parameter represents the entry for this table."
	INDEX { activeVLANEthMonTableIndex }
	::= { activeVLANEthMonTable 1 }

ActiveVLANEthMonTableEntry ::= SEQUENCE {
	activeVLANEthMonTableIndex
		Unsigned32,
	activeVLANMode
		INTEGER,
	activeAccessVLANId
		VlanId,
	activeAccessVLANPriority
		Unsigned32,
	activePortVLANId
		VlanId,
	activePortVLANPriority
		Unsigned32,
	activeuntaggedFrames
		INTEGER,
	activeuntaggedMgmtAccess
		INTEGER
}

activeVLANEthMonTableIndex  OBJECT-TYPE
	SYNTAX     Unsigned32
	MAX-ACCESS read-only
	STATUS     current
	DESCRIPTION 
		"TBD."
	::= { activeVLANEthMonTableEntry 1 }

activeVLANMode  OBJECT-TYPE
	SYNTAX     INTEGER {
		transparent (1),
		access (2),
		trunk (3)
	}
	MAX-ACCESS read-only
	STATUS     current
	DESCRIPTION 
		"TBD."
	::= { activeVLANEthMonTableEntry 2 }

activeAccessVLANId  OBJECT-TYPE
	SYNTAX     VlanId
	MAX-ACCESS read-only
	STATUS     current
	DESCRIPTION 
		"TBD."
	DEFVAL  { -1 }
	::= { activeVLANEthMonTableEntry 3 }

activeAccessVLANPriority  OBJECT-TYPE
	SYNTAX     Unsigned32 (0..7)
	MAX-ACCESS read-only
	STATUS     current
	DESCRIPTION 
		"TBD."
	DEFVAL  { 0 }
	::= { activeVLANEthMonTableEntry 4 }

activePortVLANId  OBJECT-TYPE
	SYNTAX     VlanId
	MAX-ACCESS read-only
	STATUS     current
	DESCRIPTION 
		"TBD."
	DEFVAL  { -1 }
	::= { activeVLANEthMonTableEntry 5 }

activePortVLANPriority  OBJECT-TYPE
	SYNTAX     Unsigned32 (0..7)
	MAX-ACCESS read-only
	STATUS     current
	DESCRIPTION 
		"TBD."
	DEFVAL  { 0 }
	::= { activeVLANEthMonTableEntry 6 }

activeuntaggedFrames  OBJECT-TYPE
	SYNTAX     INTEGER {
		enable (1),
		disable (2)
	}
	MAX-ACCESS read-only
	STATUS     current
	DESCRIPTION 
		"TBD."
	::= { activeVLANEthMonTableEntry 7 }

activeuntaggedMgmtAccess  OBJECT-TYPE
	SYNTAX     INTEGER {
		enable (1),
		disable (2)
	}
	MAX-ACCESS read-only
	STATUS     current
	DESCRIPTION 
		"TBD."
	::= { activeVLANEthMonTableEntry 8 }

-- Active VLAN Ethernet Trunk Monitoring table

activeVLANEthTrunkMonTable  OBJECT-TYPE
	SYNTAX SEQUENCE OF ActiveVLANEthTrunkMonTableEntry
	MAX-ACCESS not-accessible
	STATUS     current
	DESCRIPTION 
		""
	::= { activeVLAN 10 }

activeVLANEthTrunkMonTableEntry  OBJECT-TYPE
	SYNTAX 	ActiveVLANEthTrunkMonTableEntry
	MAX-ACCESS not-accessible
	STATUS     current
	DESCRIPTION 
		"This parameter represents the entry for this table."
	INDEX { activeVLANEthMonTableIndex, 
		activevlanEthTrunkMonTableSecIndex }
	::= { activeVLANEthTrunkMonTable 1 }

ActiveVLANEthTrunkMonTableEntry ::= SEQUENCE {
	activeVLANEthTrunkMonTableIndex
		Unsigned32,
	activevlanEthTrunkMonTableSecIndex
		Unsigned32,
	activeEthVLANTrunkId
		VlanId,
	activeVLANEthTrunkStatus
		INTEGER
}

activeVLANEthTrunkMonTableIndex  OBJECT-TYPE
	SYNTAX     Unsigned32
	MAX-ACCESS read-only
	STATUS     current
	DESCRIPTION 
		"TBD."
	::= { activeVLANEthTrunkMonTableEntry 1 }

activevlanEthTrunkMonTableSecIndex  OBJECT-TYPE
	SYNTAX     Unsigned32
	MAX-ACCESS read-only
	STATUS     current
	DESCRIPTION 
		"TBD."
	::= { activeVLANEthTrunkMonTableEntry 2 }

activeEthVLANTrunkId  OBJECT-TYPE
	SYNTAX     VlanId
	MAX-ACCESS read-only
	STATUS     current
	DESCRIPTION 
		"TBD."
	::= { activeVLANEthTrunkMonTableEntry 3 }

activeVLANEthTrunkStatus  OBJECT-TYPE
	SYNTAX     INTEGER {
		enable (1),
		disable (2),
		delete (3)
	}
	MAX-ACCESS read-only
	STATUS     current
	DESCRIPTION 
		"TBD."
	::= { activeVLANEthTrunkMonTableEntry 4 }

-- =============================================================================
-- The System Monitoring Subgroup: spectrumAnalyzer
-- =============================================================================

spectrumAnalyzerStartStop  OBJECT-TYPE
	SYNTAX     INTEGER {
		start (1),
		stop (2)
	}
	MAX-ACCESS read-write
	STATUS     current
	DESCRIPTION 
		"This parameter is used to start or stop spectrum analyzer."
	DEFVAL  { stop }
	::= { spectrumAnalyzer 1 }

spectrumAnalyzerChanScanTime  OBJECT-TYPE
	SYNTAX     Unsigned32 (100..60000)
	MAX-ACCESS read-write
	STATUS     current
	DESCRIPTION 
		"This parameter is used to set per channel scan time for 
		                 spectrum Analyzer. This is measured in milli seconds."
	DEFVAL  { 1000 }
	::= { spectrumAnalyzer 2 }

spectrumAnalyzerScanIterations  OBJECT-TYPE
	SYNTAX     Unsigned32 (1..1000)
	MAX-ACCESS read-write
	STATUS     current
	DESCRIPTION 
		"This parameter is used to set number of scan iterations for  
		                 spectrum analyzer."
	DEFVAL  { 1 }
	::= { spectrumAnalyzer 3 }

spectrumAnalyzerCurrentScanIterations  OBJECT-TYPE
	SYNTAX     Unsigned32 (1..1000)
	MAX-ACCESS read-only
	STATUS     current
	DESCRIPTION 
		"This parameter is used to display the current scan iterations for  
		                 spectrum analyzer."
	::= { spectrumAnalyzer 4 }

spectrumAnalyzerLastScannedTime  OBJECT-TYPE
	SYNTAX     DisplayString
	MAX-ACCESS read-only
	STATUS     current
	DESCRIPTION 
		"This parameter displays the last scanned time."
	::= { spectrumAnalyzer 5 }

-- spectrum Analyzer Results Table

spectrumAnalyzerResultsTable  OBJECT-TYPE
	SYNTAX SEQUENCE OF SpectrumAnalyzerResultsEntry
	MAX-ACCESS not-accessible
	STATUS     current
	DESCRIPTION 
		"TBD."
	::= { spectrumAnalyzer 6 }

spectrumAnalyzerResultsEntry  OBJECT-TYPE
	SYNTAX 	SpectrumAnalyzerResultsEntry
	MAX-ACCESS not-accessible
	STATUS     current
	DESCRIPTION 
		"This parameter represents the entry for this table."
	INDEX { spectrumAnalyzerTableIndex, 
		spectrumAnalyzerTableChannelIndex }
	::= { spectrumAnalyzerResultsTable 1 }

SpectrumAnalyzerResultsEntry ::= SEQUENCE {
	spectrumAnalyzerTableIndex
		Unsigned32,
	spectrumAnalyzerTableChannelIndex
		Unsigned32,
	spectrumAnalyzerChannelNo
		Unsigned32,
	spectrumAnalyzerChannelFreq
		Unsigned32,
	spectrumAnalyzerMaxRssi
		Integer32,
	spectrumAnalyzerMinRssi
		Integer32,
	spectrumAnalyzerAvgRssi
		Integer32,
	spectrumAnalyzerActivityCount
		Integer32
}

spectrumAnalyzerTableIndex  OBJECT-TYPE
	SYNTAX     Unsigned32
	MAX-ACCESS read-only
	STATUS     current
	DESCRIPTION 
		"TBD."
	::= { spectrumAnalyzerResultsEntry 1 }

spectrumAnalyzerTableChannelIndex  OBJECT-TYPE
	SYNTAX     Unsigned32
	MAX-ACCESS read-only
	STATUS     current
	DESCRIPTION 
		"TBD."
	::= { spectrumAnalyzerResultsEntry 2 }

spectrumAnalyzerChannelNo  OBJECT-TYPE
	SYNTAX     Unsigned32
	MAX-ACCESS read-only
	STATUS     current
	DESCRIPTION 
		"This parameter is used to represent the channel number."
	::= { spectrumAnalyzerResultsEntry 3 }

spectrumAnalyzerChannelFreq  OBJECT-TYPE
	SYNTAX     Unsigned32
	MAX-ACCESS read-only
	STATUS     current
	DESCRIPTION 
		"This parameter is used to represent the channel frequency."
	::= { spectrumAnalyzerResultsEntry 4 }

spectrumAnalyzerMaxRssi  OBJECT-TYPE
	SYNTAX     Integer32
	MAX-ACCESS read-only
	STATUS     current
	DESCRIPTION 
		"This parameter is used to represent the Max RSSI among all 
		                 packets detected on this channel."
	::= { spectrumAnalyzerResultsEntry 5 }

spectrumAnalyzerMinRssi  OBJECT-TYPE
	SYNTAX     Integer32
	MAX-ACCESS read-only
	STATUS     current
	DESCRIPTION 
		"This parameter is used to represent the Min RSSI among all 
		                 packets detected on this channel."
	::= { spectrumAnalyzerResultsEntry 6 }

spectrumAnalyzerAvgRssi  OBJECT-TYPE
	SYNTAX     Integer32
	MAX-ACCESS read-only
	STATUS     current
	DESCRIPTION 
		"This parameter is used to represent the Avg RSSI of all packets 
		                 detected on this channel."
	::= { spectrumAnalyzerResultsEntry 7 }

spectrumAnalyzerActivityCount  OBJECT-TYPE
	SYNTAX     Integer32
	MAX-ACCESS read-only
	STATUS     current
	DESCRIPTION 
		"This parameter is used to represent the activity on a channel."
	::= { spectrumAnalyzerResultsEntry 8 }

spectrumAnalyzerLowFreqFilter  OBJECT-TYPE
	SYNTAX     Unsigned32 (0..10000)
	MAX-ACCESS read-write
	STATUS     current
	DESCRIPTION 
		"This parameter is used to configure the low frequency filter for  
		                 spectrum analyzer."
	::= { spectrumAnalyzer 7 }

spectrumAnalyzerHighFreqFilter  OBJECT-TYPE
	SYNTAX     Unsigned32 (0..10000)
	MAX-ACCESS read-write
	STATUS     current
	DESCRIPTION 
		"This parameter is used to configure thr high frequency filter for  
		                 spectrum analyzer."
	::= { spectrumAnalyzer 8 }

spectrumAnalyzerApproxScannedTime  OBJECT-TYPE
	SYNTAX     Unsigned32
	MAX-ACCESS read-only
	STATUS     current
	DESCRIPTION 
		"This parameter is used to represent the approximate scanned time 
		                 per iteration for spectrum analyzer,
		                 units : seconds."
	::= { spectrumAnalyzer 9 }

spectrumAnalyzerAdvScanStartStop  OBJECT-TYPE
	SYNTAX     INTEGER {
		start (1),
		stop (2)
	}
	MAX-ACCESS read-write
	STATUS     current
	DESCRIPTION 
		"This parameter is used to start or stop advanced spectrum analyzer."
	DEFVAL  { stop }
	::= { spectrumAnalyzer 10 }

spectrumAnalyzerAdvScanBandwidth  OBJECT-TYPE
	SYNTAX     Unsigned32
	MAX-ACCESS read-write
	STATUS     current
	DESCRIPTION 
		"This parameter represents the bandwidth that advanced scanning is 
		 operating on. It is represented in MHz.
		         0 : Scans at all supported bandwidths "
	DEFVAL  { 0 }
	::= { spectrumAnalyzer 11 }

-- spectrum Analyzer Advanced Results Table

spectrumAnalyzerAdvResultsTable  OBJECT-TYPE
	SYNTAX SEQUENCE OF SpectrumAnalyzerAdvResultsEntry
	MAX-ACCESS not-accessible
	STATUS     current
	DESCRIPTION 
		"TBD."
	::= { spectrumAnalyzer 12 }

spectrumAnalyzerAdvResultsEntry  OBJECT-TYPE
	SYNTAX 	SpectrumAnalyzerAdvResultsEntry
	MAX-ACCESS not-accessible
	STATUS     current
	DESCRIPTION 
		"This parameter represents the entry for this table."
	INDEX { spectrumAnalyzerAdvBwdtIndex, 
		spectrumAnalyzerAdvChanIndex, 
		spectrumAnalyzerAdvDevIndex }
	::= { spectrumAnalyzerAdvResultsTable 1 }

SpectrumAnalyzerAdvResultsEntry ::= SEQUENCE {
	spectrumAnalyzerAdvBwdtIndex
		Unsigned32,
	spectrumAnalyzerAdvChanIndex
		Unsigned32,
	spectrumAnalyzerAdvDevIndex
		Unsigned32,
	spectrumAnalyzerAdvBandwidth
		Unsigned32,
	spectrumAnalyzerAdvChannel
		Unsigned32,
	spectrumAnalyzerAdvDeviceName
		DisplayString,
	spectrumAnalyzerAdvMACAddress
		MacAddress,
	spectrumAnalyzerAdvMode
		INTEGER,
	spectrumAnalyzerAdvEncrypt
		INTEGER,
	spectrumAnalyzerAdvSNR
		Unsigned32,
	spectrumAnalyzerAdvPktCount
		Unsigned32
}

spectrumAnalyzerAdvBwdtIndex  OBJECT-TYPE
	SYNTAX     Unsigned32
	MAX-ACCESS read-only
	STATUS     current
	DESCRIPTION 
		"TBD."
	::= { spectrumAnalyzerAdvResultsEntry 1 }

spectrumAnalyzerAdvChanIndex  OBJECT-TYPE
	SYNTAX     Unsigned32
	MAX-ACCESS read-only
	STATUS     current
	DESCRIPTION 
		"TBD."
	::= { spectrumAnalyzerAdvResultsEntry 2 }

spectrumAnalyzerAdvDevIndex  OBJECT-TYPE
	SYNTAX     Unsigned32
	MAX-ACCESS read-only
	STATUS     current
	DESCRIPTION 
		"TBD."
	::= { spectrumAnalyzerAdvResultsEntry 3 }

spectrumAnalyzerAdvBandwidth  OBJECT-TYPE
	SYNTAX     Unsigned32
	MAX-ACCESS read-only
	STATUS     current
	DESCRIPTION 
		"TBD."
	::= { spectrumAnalyzerAdvResultsEntry 4 }

spectrumAnalyzerAdvChannel  OBJECT-TYPE
	SYNTAX     Unsigned32
	MAX-ACCESS read-only
	STATUS     current
	DESCRIPTION 
		"TBD."
	::= { spectrumAnalyzerAdvResultsEntry 5 }

spectrumAnalyzerAdvDeviceName  OBJECT-TYPE
	SYNTAX     DisplayString
	MAX-ACCESS read-only
	STATUS     current
	DESCRIPTION 
		"TBD."
	::= { spectrumAnalyzerAdvResultsEntry 6 }

spectrumAnalyzerAdvMACAddress  OBJECT-TYPE
	SYNTAX     MacAddress
	MAX-ACCESS read-only
	STATUS     current
	DESCRIPTION 
		"TBD."
	::= { spectrumAnalyzerAdvResultsEntry 7 }

spectrumAnalyzerAdvMode  OBJECT-TYPE
	SYNTAX     INTEGER {
		ap (0),
		sta (1),
		worp (2),
		bsu (3),
		su (4),
		other (5),
		wds (6)
	}
	MAX-ACCESS read-only
	STATUS     current
	DESCRIPTION 
		"TBD."
	::= { spectrumAnalyzerAdvResultsEntry 8 }

spectrumAnalyzerAdvEncrypt  OBJECT-TYPE
	SYNTAX     INTEGER {
		no (0),
		yes (1)
	}
	MAX-ACCESS read-only
	STATUS     current
	DESCRIPTION 
		"TBD."
	::= { spectrumAnalyzerAdvResultsEntry 9 }

spectrumAnalyzerAdvSNR  OBJECT-TYPE
	SYNTAX     Unsigned32
	MAX-ACCESS read-only
	STATUS     current
	DESCRIPTION 
		"TBD."
	::= { spectrumAnalyzerAdvResultsEntry 10 }

spectrumAnalyzerAdvPktCount  OBJECT-TYPE
	SYNTAX     Unsigned32
	MAX-ACCESS read-only
	STATUS     current
	DESCRIPTION 
		"TBD."
	::= { spectrumAnalyzerAdvResultsEntry 11 }

rltStatus  OBJECT-TYPE
	SYNTAX     INTEGER {
		completed (0),
		inprogress (1)
	}
	MAX-ACCESS read-only
	STATUS     current
	DESCRIPTION 
		"This parameter show the status of rlt."
	::= { rlt 1 }
END


-- This MIB was created using NuDesign Technologies' Visual MIBuilder (Ver 5.1).
